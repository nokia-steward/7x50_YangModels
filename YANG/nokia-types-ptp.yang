module nokia-types-ptp {

    yang-version "1.1";

    namespace "urn:nokia.com:sros:ns:yang:sr:types-ptp";

    prefix "types-ptp";

    import nokia-sros-yang-extensions     { prefix "sros-ext"; }
    import nokia-types-sros               { prefix "types-sros"; }

    sros-ext:sros-major-release "rel26";
    organization "Nokia";
    contact
        "Nokia SR OS Support
         Web: <http://www.nokia.com>";
    description
        "Common PTP data types used in the SR OS management system.

         Copyright 2016 Nokia. All rights reserved. Reproduction of this document
         is authorized on the condition that the foregoing copyright notice is included.

         This nokia-types-ptp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    typedef clock-type {
        type enumeration {
            enum slave-only                     { value 1; }
            enum master-only                    { value 2; }
            enum boundary                       { value 3; }
        }
        description
            "The type of clock of the network element:
             slave-only   (1) - The system is always a slave clock in the
                                master-slave hierarchy. The system derives its
                                timing from one or more master clocks in the
                                network.
             master-only  (2) - The system is a grandmaster clock in the
                                master-slave hierarchy.  The system provides
                                timing to multiple slave clocks in the
                                network.
             boundary     (3) - The system is a boundary clock, which may be
                                anywhere in the master-slave clock hierarchy.
                                It can obtain timing from a master clock, and
                                provide timing to multiple slave clocks.";
    }

    typedef domain {
        type uint32 {
            range "0..255";
        }
        description
            "The Precision Time Protocol (PTP) domain.

             The value 0 specifies the default domain for IEEE1588-2008 specification.
             The value 4 specifies the default domain for ITU-T G.8265.1 specification.
             The value 24 specifies the default domain for ITU-T G.8275.1 specification.
             The value 44 specifies the default domain for ITU-T G.8275.2 specification.
             The value 0 specifies the default domain for IEC/IEEE 61850-9-3 specification.
             The value 254 specifies the default domain for IEEE C37.238-2017 specification.";
    }

    typedef priority {
        type uint32 {
            range "0..255";
        }
        description
            "The Precision Time Protocol (PTP) priority used both for the value to
             advertise in the Announce messages and for the local clock value in
             data set comparisons.

             It is used by the Best Master Clock Algorithm to determine which clock
             should provide timing for the network.

             The priority is rated highest (0) to lowest (255).";
    }

    typedef profile {
        type enumeration {
            enum g8265dot1-2010 {
                value 1;
                description "ITU-T G.8265.1 specification";
            }
            enum ieee1588-2008 {
                value 2;
                description "2008 version of IEEE 1588 standard";
            }
            enum g8275dot1-2014 {
                value 3;
                description "2014 version of ITU-T G.8275.1 specification";
            }
            enum g8275dot2-2016 {
                value 4;
                description "2016 version of ITU-T G.8275.2 specification";
            }
            enum iec-61850-9-3-2016 {
                value 5;
                description "2016 version of IEC/IEEE 61850-9-3 standard";
            }
            enum c37dot238-2017 {
                value 6;
                description "2017 version of C37.238 specification";
            }
        }
        description
            "The Precision Time Protocol (PTP) profile specifies the standard to
             which PTP conforms.
                  g8265dot1-2010 - conforms to the PTP profile specified in the
                                   ITU-T G.8265.1 specification
                  ieee1588-2008  - conforms to the default PTP profile specified in
                                   the IEEE 1588-2008 standard
                  g8275dot1-2014 - conforms to the PTP profile specified in the
                                   ITU-T G.8275.1 specification.
                  g8275dot2-2016 - conforms to the PTP profile specified in the
                                   ITU-T G.8275.2 specification
                  iec-61850-9-3  - conforms to the PTP profile specified in the 2016
                                   version of the IEC/IEEE 61850-9-3 specification
                  c37dot238      - conforms to PTP profile specified in the 2017
                                   version of the IEEE C37.238 specification";
    }

    typedef log-interval {
        type int32 {
            range "-128..127";
        }
        description
            "The interval between PTP packets, or equivalently a packet rate.
             Is is the logarithm to the base 2 of the interval in seconds.

             For example, -7 specifies a rate of 128 packets per second, and
             +4 specifies a packet rate of 1 packet every 16 seconds.";
    }

    typedef clock-identity-type {
        type types-sros:hex-string;
        description "Derived data type to identify a clock.";
    }

    typedef ptp-profile-identifier-type {
        type types-sros:hex-string;
        description "The PTP profile identifier for a PTP clock or a PTP port on a PTP clock.";
    }

    typedef port-encap-type {
        type enumeration {
            enum unknown                        { value 0; }
            enum null                           { value 1; }
            enum dot1q                          { value 2; }
            enum mpls                           { value 3; }
            enum qinq                           { value 10; }
            enum cem                            { value 13; }
            enum reserved14                     { value 14; }
            enum raw                            { value 15; }
            enum cellular                       { value 16; }
            enum wlan                           { value 17; }
            enum bcp-null                       { status obsolete; }
            enum bcp-dot1q                      { status obsolete; }
            enum ipcp                           { status obsolete; }
            enum frame-relay                    { status obsolete; }
            enum ppp-auto                       { status obsolete; }
            enum atm                            { status obsolete; }
            enum wan-mirror                     { status obsolete; }
            enum cisco-hdlc                     { status obsolete; }
        }
        description
            "The type of encapsulation protocol configured on a
             port's network interface.

             When the encap type has a value of 'null',
             frames received will not carry any tags
             or labels and as a result only one service can be
             configured on this port.  Sometimes this is referred to
             as raw Ethernet packets.

             When the encap type has a value of 'dot1q', ingress frames
             carry 802.1q tags where each different tag can signify a
             different service.

              When the encap type has a value of 'bcp-null', BCP is used on the SONET
              path as the Network Control Protocol (NCP). The BCP IEEE 802 Tagged Frame
              Configuration Option (type 8) is negotiated to 'enabled'. VLAN tagged
              frames are allowed into the SONET path. Only a single SAP can be
              associated with the SONET path.

              When the encap type has a value of 'bcp-dot1q', BCP is used as the
              Network Control Protocol (NCP). The BCP IEEE 802 tagged Frame Configuration
              Option (type 8) is negotiated to 'enabled'. VLAN tagged frames are allowed
              on the SONET path. This encapsulation type is required when multiple SAPs are
              defined on the SONET path where each one is service delimited by a
              provisioned Dot1q tag. When 'bcp-dot1q' is specified, BCP does not enter the
              'open' state unless the far end peer also supports 'bcp-dot1q'. This allows
              an LCP negotiation to transmit configuration request and confirmation
              messages to enable this feature.

              When the encap type has a value of 'ipcp', BCP will not be used on this SONET
              path. Internet Protocol Control Protocol (IPCP) is used instead.

              When the encap type has a value of 'frame-relay', Frame Relay is the expected
              encapsulation.

              When the encap type has a value of 'ppp-auto', IPCP is automatically enabled.
              This encap type is only valid on ports/paths in network mode.

              When the encap type has a value of 'atm', the encapsulation on the port is
              ATM. The 'atm' encap type is also used when mirroring ATM ports.

              When the encap type has a value of 'wan-mirror', the port is used for
              mirroring of frame-relay and POS ports. On such ports no link management
              protocol would run.

              When the encap type has a value of 'cisco-hdlc', the Cisco HDLC encapsulation
              is applied.

             When the encap type has a value of 'cem', encapsulation of
             frames will be circuit emulation.  This is used to support transparent
             transmission of frames.  This encap type is only valid
             on 'tdm' or 'sonet' ports in access mode.

             When the encap type has a value of 'raw', data does not
             necessarily carry any tags, headers or any other form of delimiter.
             This encap type is only valid on access ports supporting serial data.

             When the encap type has a value of 'cellular', packets on the
             port use cellular encapsulation.  This encapsulation is only valid
             on cellular ports.";
    }

    typedef time-interval-type {
        type int64;
        description
            "Derived data type for time interval, represented in units of
              nanoseconds and multiplied by 2^16.";
    }

    typedef timestamp-reference-point {
        type enumeration {
            enum unknown                        { value 0; }
            enum port                           { value 1; }
            enum cpm                            { value 2; }
        }
        description
            "The reference point where a PTP event packet is timestamped in the SROS system:
                unknown (0) - The reference point for the PTP timestamp has not yet
                              been determined.
                port    (1) - The PTP packet's timestamp was taken at the physical
                              port, between the MAC and the PHY.
                cpm     (2) - The PTP packet's timestamp was taken in software in
                              the operating system kernel on the CPM card.";
    }

    typedef announce-packet-tlv-type {
        type enumeration {
            enum ieee-c37-238                   { value 1; }
            enum alternate-time-offset-indicator { value 2; }
            enum other                          { value 3; }
        }
        description "Specifies the announce tlv type.";
    }

}
