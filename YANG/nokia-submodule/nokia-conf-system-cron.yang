submodule nokia-conf-system-cron {

    yang-version "1.1";

    belongs-to nokia-conf { prefix "conf"; }

    import ietf-yang-types                { prefix "yang"; }
    import nokia-sros-yang-extensions     { prefix "sros-ext"; }
    import nokia-types-sros               { prefix "types-sros"; }
    import nokia-types-system             { prefix "types-system"; }

    include nokia-conf-groups;

    sros-ext:sros-major-release "rel26";
    organization "Nokia";
    contact
        "Nokia SR OS Support
         Web: <http://www.nokia.com>";
    description
        "Nokia YANG Data model to configure system cron on SR OS based routers.

         Copyright 2016 Nokia. All rights reserved. Reproduction of this document
         is authorized on the condition that the foregoing copyright notice is included.

         This nokia-conf-system-cron YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping conf-system-cron {
        container cron {
            description "Enter the cron context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list schedule {
                key "schedule-name owner";
                max-elements 255;
                description "Enter the schedule list instance";

                leaf schedule-name {
                    type types-sros:named-item;
                    description "Schedule name";
                }

                leaf owner {
                    type types-sros:named-item;
                    description "Schedule owner";
                }

                leaf admin-state {
                    type types-sros:admin-state;
                    default "disable";
                    description "Administrative state of the CRON schedule";
                }

                leaf description {
                    type types-sros:description;
                    description "Text description";
                }

                leaf count {
                    type uint32 {
                        range "1..65535";
                    }
                    description "Number of times to repeat a periodic schedule run";
                }

                leaf interval {
                    type uint32 {
                        range "30..42949672";
                    }
                    units "seconds";
                    description "Time between each periodic schedule run";
                }

                leaf type {
                    type enumeration {
                        enum periodic                       { value 1; }
                        enum calendar                       { value 2; }
                        enum oneshot                        { value 3; }
                    }
                    default "periodic";
                    description "Schedule type";
                }

                leaf-list day-of-month {
                    type int32 {
                        range "-31..-1|1..31";
                    }
                    max-elements 62;
                    description "Days in a month when a schedule runs";
                }

                leaf-list hour {
                    type uint32 {
                        range "0..23";
                    }
                    max-elements 24;
                    description "Hours within a day when the schedule runs";
                }

                leaf-list minute {
                    type uint32 {
                        range "0..59";
                    }
                    max-elements 60;
                    description "Minutes in an hour when the schedule runs";
                }

                leaf-list month {
                    type union {
                        type enumeration {
                            enum january                        { value 1; }
                            enum february                       { value 2; }
                            enum march                          { value 3; }
                            enum april                          { value 4; }
                            enum may                            { value 5; }
                            enum june                           { value 6; }
                            enum july                           { value 7; }
                            enum august                         { value 8; }
                            enum september                      { value 9; }
                            enum october                        { value 10; }
                            enum november                       { value 11; }
                            enum december                       { value 12; }
                        }
                        type uint32 {
                            range "1..12";
                        }
                    }
                    max-elements 12;
                    description "Months when the schedule runs";
                }

                leaf-list weekday {
                    type union {
                        type enumeration {
                            enum sunday                         { value 1; }
                            enum monday                         { value 2; }
                            enum tuesday                        { value 3; }
                            enum wednesday                      { value 4; }
                            enum thursday                       { value 5; }
                            enum friday                         { value 6; }
                            enum saturday                       { value 7; }
                        }
                        type uint32 {
                            range "1..7";
                        }
                    }
                    max-elements 7;
                    description "Weekdays when the schedule runs";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container script-policy {
                    description "Enter the script-policy context";

                    leaf name {
                        type types-sros:named-item;
                        description "CLI script policy name";
                    }

                    leaf owner {
                        type types-sros:named-item;
                        description "Script policy owner";
                    }

                } // container script-policy

                container end-time {
                    description "Enter the end-time context";

                    choice date-or-dayname-time {
                        case date-and-time {

                            leaf date-and-time {
                                type yang:date-and-time;
                                description "Date and time to stop triggering the schedule";
                            }

                        }
                        case dayname-time {

                            leaf day {
                                type enumeration {
                                    enum sunday                         { value 0; }
                                    enum monday                         { value 1; }
                                    enum tuesday                        { value 2; }
                                    enum wednesday                      { value 3; }
                                    enum thursday                       { value 4; }
                                    enum friday                         { value 5; }
                                    enum saturday                       { value 6; }
                                }
                                description "Day to stop triggering the schedule";
                            }

                            leaf time {
                                type types-system:hours-minutes-twenty-four;
                                description "Time to stop triggering the schedule";
                            }

                        }
                    }
                } // container end-time

            } // list schedule

        } // container cron

    } // grouping conf-system-cron

}
