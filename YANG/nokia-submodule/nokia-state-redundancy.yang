submodule nokia-state-redundancy {

    yang-version "1.1";

    belongs-to nokia-state { prefix "state"; }

    import ietf-yang-types                { prefix "yang"; }
    import nokia-sros-yang-extensions     { prefix "sros-ext"; }
    import nokia-types-mcr                { prefix "types-mcr"; }
    import nokia-types-redundancy         { prefix "types-redundancy"; }
    import nokia-types-services           { prefix "types-services"; }
    import nokia-types-sros               { prefix "types-sros"; }
    import nokia-types-system             { prefix "types-system"; }

    include nokia-state-isa;
    include nokia-state-lag;

    sros-ext:sros-major-release "rel26";
    organization "Nokia";
    contact
        "Nokia SR OS Support
         Web: <http://www.nokia.com>";
    description
        "Nokia YANG Data model with operational state for redundancy configuration on SR OS based routers.

         Copyright 2016 Nokia. All rights reserved. Reproduction of this document
         is authorized on the condition that the foregoing copyright notice is included.

         This nokia-state-redundancy YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping state-redundancy {
        container redundancy {
            description "Enter the redundancy context";

            leaf switchover-exec-status {
                type types-system:script-state;
                description
                    "The results of executing the CLI script file specified
                     in 'switchover-exec'.";
            }

            leaf snmp-index-sync-mismatch {
                type boolean;
                description
                    "If SNMP index persistency is enabled on redundant CPMs and
                     the system is not configured to synchronize files between CPMs,
                     this parameter is true. It is false otherwise.";
            }

            container mgmt-ethernet {
                description "Enter the mgmt-ethernet context";

                leaf redundancy-standby {
                    type boolean;
                    description
                        "Indicates whether or not the management of the node
                         is operating from the standby CPM's management Ethernet port.";
                }

            } // container mgmt-ethernet

            container multi-chassis {
                description "Enter the multi-chassis context";

                list ipsec-domain {
                    key "id";
                    description "Enter the ipsec-domain list instance";

                    leaf id {
                        type uint32 {
                            range "1..255";
                        }
                        description "Specify ipsec-domain Id";
                    }

                    leaf activity-state {
                        type types-redundancy:mc-ipsec-activity-state;
                        description
                            "Indicates the result of the activity election between this ipsec domain entity
                             and its peers.";
                    }

                    leaf protection-status {
                        type types-redundancy:tunnel-group-protection-status;
                        description
                            "Indicates the readiness of the ipsec domain to perform a forced switchover
                             of active/standby state from the current active chassis to the standby chassis.";
                    }

                    leaf current-active {
                        type types-sros:ip-address;
                        description "Indicates the router id of the current active chassis for this domain.";
                    }

                    leaf local-router-id {
                        type types-sros:ip-address;
                        description "Indicates local router id of the domain.";
                    }

                    leaf dynamic-installed {
                        type yang:gauge32;
                        description
                            "Indicates the number of dynamic multi-chassis tunnels installed
                             on this ipsec-domain.";
                    }

                    leaf dynamic-installing {
                        type yang:gauge32;
                        description
                            "Indicates the number of dynamic multi-chassis tunnels being
                             installed on this ipsec-domain.";
                    }

                    leaf dynamic-standby-dormant {
                        type yang:gauge32;
                        description
                            "Indicates the number of dynamic multi-chassis tunnels that
                             are in the standby dormant state on this ipsec-domain.";
                    }

                    leaf dynamic-await-conf {
                        type yang:gauge32;
                        description
                            "Indicates the number of dynamic multi-chassis tunnels awaiting
                             configuration on this ipsec-domain.";
                    }

                    leaf dynamic-failed {
                        type yang:gauge32;
                        description
                            "Indicates the number of dynamic multi-chassis tunnels failed
                             to install on this ipsec-domain.";
                    }

                    leaf installed {
                        type yang:gauge32;
                        description
                            "Indicates the number of static multi-chassis tunnels installed
                             on this ipsec-domain.";
                    }

                    leaf installing {
                        type yang:gauge32;
                        description
                            "Indicates the number of static multi-chassis tunnels being
                             installed on this ipsec-domain.";
                    }

                    leaf standby-dormant {
                        type yang:gauge32;
                        description
                            "Indicates the number of static multi-chassis tunnels that
                             are in the standby dormant state on this ipsec-domain.";
                    }

                    leaf await-conf {
                        type yang:gauge32;
                        description
                            "Indicates the number of static multi-chassis tunnels awaiting
                             configuration on this ipsec-domain.";
                    }

                    leaf failed {
                        type yang:gauge32;
                        description
                            "Indicates the number of static multi-chassis tunnels failed
                             to install on this ipsec-domain.";
                    }

                } // list ipsec-domain

                container mc-endpoint {
                    description "Enter the mc-endpoint context";

                    container statistics {
                        description "Enter the statistics context";

                        container received {
                            description "Enter the received context";

                            leaf packets {
                                type yang:counter32;
                                description "The number of control packets with valid authentication were received.";
                            }

                            leaf keep-alive {
                                type yang:counter32;
                                description "The number of keep-alive messages received.";
                            }

                            leaf config {
                                type yang:counter32;
                                description "The number of configuration packets received.";
                            }

                            leaf peer-config {
                                type yang:counter32;
                                description "The number of peer configuration packets received.";
                            }

                            leaf state {
                                type yang:counter32;
                                description "The number of packets indicating the lag state received.";
                            }

                        } // container received

                        container dropped {
                            description "Enter the dropped context";

                            leaf too-short {
                                type yang:counter32;
                                description "The number of control packets dropped because packet was too small.";
                            }

                            leaf tlv-invalid-size {
                                type yang:counter32;
                                description "The number of control packets dropped because of invalid size.";
                            }

                            leaf out-of-sequence {
                                type yang:counter32;
                                description "The number of control packets dropped because they were out of sequence.";
                            }

                            leaf unknown-tlv {
                                type yang:counter32;
                                description "The number of control packets dropped because of unknown TLV.";
                            }

                            leaf invalid-endpoint-id {
                                type yang:counter32;
                                description
                                    "The number of control packets dropped because they refer to an invalid
                                     endpoint id.";
                            }

                            leaf failed-md5 {
                                type yang:counter32;
                                description "The number of control packets dropped because they failed MD5 authentication.";
                            }

                            leaf peer-not-found {
                                type yang:counter32;
                                description "The number of control packets dropped because no peer was assigned or peer did not match.";
                            }

                            leaf keep-alive-task {
                                type yang:counter32;
                                description "The number of control packets dropped with invalid size, authentication or unknown peer.";
                            }

                            leaf verification-failed {
                                type yang:counter32;
                                description "The number of control packets dropped because of invalid formatting.";
                            }

                            leaf unknown-peer {
                                type yang:counter32;
                                description "The number of control packets dropped because they are coming from an unknown peer.";
                            }

                        } // container dropped

                        container transmitted {
                            description "Enter the transmitted context";

                            leaf packets {
                                type yang:counter32;
                                description "The number of control packets transmitted.";
                            }

                            leaf keep-alive {
                                type yang:counter32;
                                description "The number of keep-alive messages transmitted.";
                            }

                            leaf peer-config {
                                type yang:counter32;
                                description "The number of peer configuration packets transmitted.";
                            }

                            leaf failed {
                                type yang:counter32;
                                description "The number of packets failed to be transmitted.";
                            }

                            leaf config {
                                type yang:counter32;
                                description "The number of configuration packets transmitted.";
                            }

                            leaf state {
                                type yang:counter32;
                                description "The number of packets indicating lag state transmitted.";
                            }

                        } // container transmitted

                    } // container statistics

                    list endpoint {
                        key "id";
                        description "Enter the endpoint list instance";

                        leaf id {
                            type uint32 {
                                range "1..4294967295";
                            }
                            description "Multi-chassis end-point identifier.";
                        }

                        container statistics {
                            description "Enter the statistics context";

                            container received {
                                description "Enter the received context";

                                leaf config {
                                    type yang:counter32;
                                    description "The number of endpoint config packets received on this system for this endpoint.";
                                }

                                leaf state {
                                    type yang:counter32;
                                    description "The number of endpoint state packets received on this system for this endpoint.";
                                }

                            } // container received

                            container transmitted {
                                description "Enter the transmitted context";

                                leaf config {
                                    type yang:counter32;
                                    description "The number of endpoint config packets transmitted on this system for this endpoint.";
                                }

                                leaf state {
                                    type yang:counter32;
                                    description "The number of endpoint state packets transmitted on this system for this endpoint.";
                                }

                                leaf failed {
                                    type yang:counter32;
                                    description "The number of endpoint control packets failed to be transmitted on this system for this endpoint.";
                                }

                            } // container transmitted

                        } // container statistics

                    } // list endpoint

                } // container mc-endpoint

                container mc-ring {
                    description "Enter the mc-ring context";

                    container statistics {
                        description "Enter the statistics context";

                        leaf tx-packets {
                            type yang:counter32;
                            description "The number of signalling packets transmitted by this system.";
                        }

                        leaf tx-no-buffer {
                            type yang:counter32;
                            description "The number of signalling packets that could not be transmitted by this system due to lack of packet buffers.";
                        }

                        leaf tx-failures {
                            type yang:counter32;
                            description "The number of signalling packets that could not be transmitted by this system due to transmission failure.";
                        }

                        leaf tx-unknown-dest {
                            type yang:counter32;
                            description "The number of signalling packets that could not be transmitted by this system because the destination was unknown.";
                        }

                        leaf rx-packets {
                            type yang:counter32;
                            description "The number of signalling packets received by this system.";
                        }

                        leaf rx-too-short {
                            type yang:counter32;
                            description "The number of signalling packets received by this system that were too short.";
                        }

                        leaf rx-wrong-auth {
                            type yang:counter32;
                            description "The number of signalling packets received by this system with invalid authentication.";
                        }

                        leaf rx-invalid-tlv {
                            type yang:counter32;
                            description "The number of signalling packets received by thsi system with invalid TLV.";
                        }

                        leaf rx-incomplete {
                            type yang:counter32;
                            description "The number of signalling packets received by this system that were incomplete.";
                        }

                        leaf rx-unknown-type {
                            type yang:counter32;
                            description "The number of signalling packets received by this system that were of unknown type.";
                        }

                        leaf rx-unknown-peer {
                            type yang:counter32;
                            description "The number of signalling packets received by this system that were related to an unknown peer.";
                        }

                        leaf rx-unknown-ring {
                            type yang:counter32;
                            description "The number of signalling packets received by this system that were related to an unknown ring.";
                        }

                        leaf rx-unknown-ring-node {
                            type yang:counter32;
                            description "The number of signalling packets received by this system that were related to an unknown ring node.";
                        }

                        leaf rx-delivered-to-peer {
                            type yang:counter32;
                            description "The number of signalling packets received by this system that were correctly delivered to their peer.";
                        }

                        leaf rx-delivered-to-ring {
                            type yang:counter32;
                            description "The number of signalling packets received by this system that were correctly delivered to their ring.";
                        }

                        leaf rx-delivered-to-ring-node {
                            type yang:counter32;
                            description "The number of signalling packets received by this system that were correctly delivered to their ring node.";
                        }

                        leaf missed-config-events {
                            type yang:counter32;
                            description "The number of missed configuration events on this system.";
                        }

                        leaf missed-bfd-events {
                            type yang:counter32;
                            description "The number of missed BFD events on this system.";
                        }

                    } // container statistics

                } // container mc-ring

                list peer {
                    key "ip-address";
                    description "Enter the peer list instance";

                    leaf ip-address {
                        type types-sros:ip-unicast-address;
                        description "Attribute IP address for peer.";
                    }

                    leaf source-oper-address {
                        type types-sros:ip-address;
                        description
                            "Indicates the operational source address in use
                             to communicate with the multi-chassis peer.";
                    }

                    leaf rings-oper-state {
                        type types-sros:oper-state;
                        description
                            "Indicates the operational state of this multi-chassis peer
                             with respect to multi-chassis ring operation.";
                    }

                    container options {
                        description "Enter the options context";

                        container sub-mgmt {
                            description "Enter the sub-mgmt context";

                            container dhcp-leasetime-threshold {
                                description "Enter the dhcp-leasetime-threshold context";

                                leaf active {
                                    type types-sros:time-duration;
                                    description
                                        "The active dhcp-leasetime-threshold of this multi-chassis peer.
                                         It is the minimum between the local configured dhcp-leasetime-threshold
                                         and the received remote dhcp-leatime-threshold.";
                                }

                                leaf remote {
                                    type types-sros:time-duration;
                                    description "The dhcp-leasetime-threshold recieved from this multi-chassis peer.";
                                }

                            } // container dhcp-leasetime-threshold

                        } // container sub-mgmt

                    } // container options

                    container mc-endpoint {
                        description "Enter the mc-endpoint context";

                        leaf oper-state {
                            type types-sros:oper-state;
                            description "Operational status of the multi-chassis endpoint peer.";
                        }

                        leaf passive-mode-operation {
                            type boolean;
                            description
                                "Indicates whether passive-mode behavior is operationally enabled on this multi-chassis
                                 endpoint peer.";
                        }

                        leaf peer-reference-counter {
                            type uint32;
                            description "The number of service endpoints referencing this multi-chassis endpoint.";
                        }

                        container statistics {
                            description "Enter the statistics context";

                            container received {
                                description "Enter the received context";

                                leaf packets {
                                    type yang:counter32;
                                    description "The number of control packets with valid authentication were received.";
                                }

                                leaf keep-alive {
                                    type yang:counter32;
                                    description "The number of keep-alive messages received.";
                                }

                                leaf config {
                                    type yang:counter32;
                                    description "The number of configuration packets received.";
                                }

                                leaf peer-config {
                                    type yang:counter32;
                                    description "The number of peer configuration packets received.";
                                }

                                leaf state {
                                    type yang:counter32;
                                    description "The number of packets indicating the lag state received.";
                                }

                            } // container received

                            container dropped {
                                description "Enter the dropped context";

                                leaf too-short {
                                    type yang:counter32;
                                    description "The number of control packets dropped because packet was too small.";
                                }

                                leaf tlv-invalid-size {
                                    type yang:counter32;
                                    description "The number of control packets dropped because of invalid size.";
                                }

                                leaf out-of-sequence {
                                    type yang:counter32;
                                    description "The number of control packets dropped because they were out of sequence.";
                                }

                                leaf unknown-tlv {
                                    type yang:counter32;
                                    description "The number of control packets dropped because of unknown TLV.";
                                }

                                leaf invalid-endpoint-id {
                                    type yang:counter32;
                                    description
                                        "The number of control packets dropped because they refer to an invalid
                                         endpoint id.";
                                }

                                leaf failed-md5 {
                                    type yang:counter32;
                                    description "The number of control packets dropped because they failed MD5 authentication.";
                                }

                                leaf peer-not-found {
                                    type yang:counter32;
                                    description "The number of control packets dropped because no peer was assigned or peer did not match.";
                                }

                                leaf peer-disabled {
                                    type yang:counter32;
                                    description
                                        "The number of control packets dropped from the peer
                                         because the peer was administratively disabled.";
                                }

                            } // container dropped

                            container transmitted {
                                description "Enter the transmitted context";

                                leaf packets {
                                    type yang:counter32;
                                    description "The number of control packets transmitted.";
                                }

                                leaf keep-alive {
                                    type yang:counter32;
                                    description "The number of keep-alive messages transmitted.";
                                }

                                leaf peer-config {
                                    type yang:counter32;
                                    description "The number of peer configuration packets transmitted.";
                                }

                                leaf failed {
                                    type yang:counter32;
                                    description "The number of packets failed to be transmitted.";
                                }

                            } // container transmitted

                        } // container statistics

                    } // container mc-endpoint

                    container sync {
                        description "Enter the sync context";

                        leaf oper-state {
                            type types-sros:oper-state;
                            description
                                "Indicates the operational state of the synchronization
                                 protocol with the multi-chassis peer.";
                        }

                        leaf oper-flags {
                            type bits {
                                bit sync-admin-down                { position 0; }
                                bit peer-admin-down                { position 1; }
                                bit connection-down                { position 2; }
                                bit internal-error                 { position 3; }
                                bit mcs-version-mismatch           { position 4; }
                                bit platform-mismatch              { position 5; }
                                bit app-version-mismatch           { position 6; }
                                bit app-support-mismatch           { position 7; }
                                bit omcr-version-mismatch          { position 8; }
                                bit omcr-standby-standby           { position 9; }
                                bit omcr-num-entries-high          { position 10; }
                                bit decryption-error               { position 11; }
                            }
                            description
                                "Indicates the reason that the synchronization protocol
                                 with the multi-chassis peer is down.";
                        }

                        leaf sync-state {
                            type enumeration {
                                enum in-sync                        { value 1; }
                                enum sync-in-progress               { value 2; }
                                enum out-of-sync                    { value 3; }
                            }
                            description "Indicates the status of the synchronization process.";
                        }

                        leaf last-sync-time {
                            type yang:date-and-time;
                            description
                                "Indicates the sysUpTime at the time the last synchronization
                                 with the peer was successful.";
                        }

                        container statistics {
                            description "Enter the statistics context";

                            leaf entries-number {
                                type yang:counter32;
                                description
                                    "Indicates the total number of entries in the MCS database
                                     per multi-chassis peer.";
                            }

                            leaf localy-deleted-entries {
                                type yang:counter32;
                                description
                                    "Indicates the total number of locally deleted entries
                                     in the MCS database per multi-chassis peer.

                                     Locally deleted entries are entries that are not being used
                                     by the local MCS client application.";
                            }

                            leaf alarmed-entries {
                                type yang:counter32;
                                description
                                    "Indicates the total number of alarmed entries
                                     in the MCS database per multi-chassis peer.

                                     Entries with an alarm are entries that are not being used by
                                     the local client application due to resource constraints.";
                            }

                            leaf remote-entries-number {
                                type yang:counter32;
                                description
                                    "Indicates the total number of entries in the MCS database
                                     of the multi-chassis peer.";
                            }

                            leaf remote-localy-deleted-entries {
                                type yang:counter32;
                                description
                                    "Indicates the total number of locally deleted entries
                                     in the MCS database of the multi-chassis peer.

                                     Locally deleted entries are entries that are not being used
                                     by the remote MCS client application.";
                            }

                            leaf remote-alarmed-entries {
                                type yang:counter32;
                                description
                                    "Indicates the total number of alarmed entries in
                                     the MCS database of the  multi-chassis peer.

                                     Entries with an alarm are entries that are not being used by
                                     the remote client application due to resource constraints.";
                            }

                            leaf omcr-standby {
                                type yang:counter32;
                                description
                                    "Indicates the number of Oversubscribed Multi-Chassis Redundancy
                                     (OMCR) standby entries in the MCS database of this
                                     multi-chassis peer.";
                            }

                            leaf omcr-alarmed {
                                type yang:counter32;
                                description
                                    "Indicates the number of Oversubscribed Multi-Chassis Redundancy
                                     (OMCR) alarmed entries in the MCS database of this
                                     multi-chassis peer.";
                            }

                            leaf omcr-remote-standby {
                                type yang:counter32;
                                description
                                    "Indicates the number of Oversubscribed Multi-Chassis Redundancy
                                     (OMCR) standby entries reported by the remote MCR system.";
                            }

                            leaf omcr-remote-alarmed {
                                type yang:counter32;
                                description
                                    "Indicates the number of Oversubscribed Multi-Chassis Redundancy
                                     (OMCR) alarmed entries reported by the remote MCR system.";
                            }

                            container transmission {
                                description "Enter the transmission context";

                                leaf tx-all {
                                    type yang:counter32;
                                    description
                                        "The total number of packets transmitted to the multi-chassis
                                         peer.";
                                }

                                leaf tx-hello {
                                    type yang:counter32;
                                    description
                                        "The number of hello packets transmitted to the multi-chassis
                                         peer.";
                                }

                                leaf tx-data {
                                    type yang:counter32;
                                    description
                                        "The number of data packets transmitted to the multi-chassis
                                         peer.";
                                }

                                leaf tx-other {
                                    type yang:counter32;
                                    description
                                        "The number of all other packet types transmitted
                                         to the multi-chassis peer.";
                                }

                                leaf tx-error {
                                    type yang:counter32;
                                    description "The number of packet transmission errors.";
                                }

                                leaf rx-all {
                                    type yang:counter32;
                                    description
                                        "The total number of packets received from the multi-chassis
                                         peer.";
                                }

                                leaf rx-hello {
                                    type yang:counter32;
                                    description
                                        "The number of hello packets received from the multi-chassis
                                         peer.";
                                }

                                leaf rx-data {
                                    type yang:counter32;
                                    description
                                        "The number of hello packets received from the multi-chassis
                                         peer.";
                                }

                                leaf rx-other {
                                    type yang:counter32;
                                    description
                                        "The number of all other packet types received
                                         from the multi-chassis peer.";
                                }

                                leaf rx-error {
                                    type yang:counter32;
                                    description
                                        "The number of erroneous packets received from
                                         the multi-chassis peer.";
                                }

                                leaf rx-error-header {
                                    type yang:counter32;
                                    description
                                        "The number of packets with header decode errors received
                                         from the multi-chassis peer.";
                                }

                                leaf rx-error-body {
                                    type yang:counter32;
                                    description
                                        "The number of packets with body decode errors received
                                         from the multi-chassis peer.";
                                }

                                leaf rx-error-sequence-number {
                                    type yang:counter32;
                                    description
                                        "The number of packets with sequence number errors received
                                         from the multi-chassis peer.";
                                }

                            } // container transmission

                            list client-application {
                                key "application";
                                description "Enter the client-application list instance";

                                leaf application {
                                    type types-redundancy:mc-application;
                                    description "The type of application using multi-chassis synchronization.";
                                }

                                leaf num-entries {
                                    type yang:counter32;
                                    description
                                        "The total number of entries in the MCS database per
                                         multi-chassis peer for a particular application.";
                                }

                                leaf locally-deleted-entries {
                                    type yang:counter32;
                                    description
                                        "The number of locally deleted entries in the MCS database
                                         per multi-chassis peer for a particular application. Locally
                                         deleted entries are entries that are not being used
                                         by the local MCS client application.";
                                }

                                leaf alarmed-entries {
                                    type yang:counter32;
                                    description
                                        "The number of alarmed entries in the MCS database
                                         per multi-chassis peer for a particular application. Entries
                                         with an alarm are entries that are not being used by the local
                                         client application due to resource constraints.";
                                }

                                leaf remote-num-entries {
                                    type yang:counter32;
                                    description
                                        "The total number of entries in the MCS database
                                         on the multi-chassis peer for a particular application.";
                                }

                                leaf remote-locally-deleted-entries {
                                    type yang:counter32;
                                    description
                                        "The number of locally deleted entries in the MCS database onto
                                         he multi-chassis peer for a particular application. Locally
                                         deleted entries are entries that are not being used by the
                                         remote MCS client application.";
                                }

                                leaf remote-alarmed-entries {
                                    type yang:counter32;
                                    description
                                        "The number of alarmed entries in the MCS database
                                         on the multi-chassis peer for a particular application.
                                         Entries with an alarm are entries that are not being used
                                         by the remote client application due to resource constraints.";
                                }

                                leaf omcr-standby {
                                    type yang:counter32;
                                    description
                                        "The number of Oversubscribed Multi-Chassis Redundancy (OMCR)
                                         standby entries in the MCS database of this multi-chassis peer
                                         for this particular application.";
                                }

                                leaf omcr-alarmed {
                                    type yang:counter32;
                                    description
                                        "The number of Oversubscribed Multi-Chassis Redundancy (OMCR)
                                         alarmed entries in the MCS database of this multi-chassis peer
                                         for this particular application.";
                                }

                                leaf omcr-remote-standby {
                                    type yang:counter32;
                                    description
                                        "The number of Oversubscribed Multi-Chassis Redundancy (OMCR)
                                         standby entries for this particular application reported
                                         by the remote MCR system.";
                                }

                                leaf omcr-remote-alarmed {
                                    type yang:counter32;
                                    description
                                        "The number of Oversubscribed Multi-Chassis Redundancy (OMCR)
                                         alarmed entries for this particular application reported
                                         by the remote MCR system.";
                                }

                            } // list client-application

                        } // container statistics

                    } // container sync

                    container mc-ipsec {
                        description "Enter the mc-ipsec context";

                        list domain {
                            key "id";
                            description "Enter the domain list instance";

                            leaf id {
                                type leafref {
                                    path "../../../../ipsec-domain/id";
                                }
                                description "Specify ipsec-domain Id";
                            }

                            leaf oper-state {
                                type types-sros:oper-state;
                                description "Indicate operational state of this multi-chassis peer with respect to this ipsec-domain.";
                            }

                            leaf out-of-service-reason {
                                type types-sros:description;
                                description
                                    "Indicates the reason why peer ipsec domain oper state
                                     is out of service.";
                            }

                            leaf remote-active-state {
                                type types-redundancy:mc-ipsec-activity-state;
                                description "Indicates the activity state of the remote ipsec-domain reachable via this multi-chassis peer.";
                            }

                            leaf remote-router-id {
                                type types-sros:ip-address;
                                description "Indicates remote router id of the domain.";
                            }

                            leaf remote-designated-role {
                                type enumeration {
                                    enum standby                        { value 1; }
                                    enum active                         { value 2; }
                                    enum unknown                        { value 3; }
                                }
                                description "Indicated the designated role of remote ipsec-domain reachable via this multi-chassis peer.";
                            }

                        } // list domain

                        list tunnel-group {
                            key "tunnel-group-id";
                            description "Enter the tunnel-group list instance";

                            leaf tunnel-group-id {
                                type leafref {
                                    path "../../../../../../isa/tunnel-group/id";
                                }
                                description "Id of the tunnel group.";
                            }

                            leaf oper-state {
                                type types-sros:oper-state;
                                description "Indicate operational state of tunnel-group communicating.";
                            }

                            leaf master-state {
                                type types-redundancy:tunnel-group-master-state;
                                description
                                    "Indicate the result of the mastership election between this
                                     tunnel group entity and its peer.";
                            }

                            leaf out-of-service-reason {
                                type types-sros:description;
                                description
                                    "Indicates the reason why tunnel group oper state
                                     is out of service.";
                            }

                            leaf protect-status {
                                type types-redundancy:tunnel-group-protection-status;
                                description
                                    "Indicates the readiness of the tunnel group to perform a forced
                                     switchover of mastership from the current master chassis
                                     to the standby chassis.";
                            }

                            leaf dynamic-installed {
                                type uint32;
                                description
                                    "The number of dynamic multi-chassis tunnel installed on this
                                     tunnel-group to be synchronized on this multi-chassis peer.";
                            }

                            leaf dynamic-installing {
                                type uint32;
                                description
                                    "The number of dynamic multi-chassis tunnel being installed
                                     on this tunnel-group to be synchronized on this
                                     multi-chassis peer.";
                            }

                            leaf dynamic-await-conf {
                                type uint32;
                                description
                                    "The number of dynamic multi-chassis tunnel awaiting
                                     configuration on this tunnel-group to be synchronized
                                     on this multi-chassis peer.";
                            }

                            leaf dynamic-failed {
                                type uint32;
                                description
                                    "The number of dynamic multi-chassis tunnel failed to install
                                     on this tunnel-group to be synchronized on this
                                     multi-chassis peer.";
                            }

                            leaf installed {
                                type uint32;
                                description
                                    "The number of static multi-chassis tunnel installed on this
                                     tunnel-group to be synchronized on this multi-chassis peer.";
                            }

                            leaf installing {
                                type uint32;
                                description
                                    "The number of static multi-chassis tunnel being installed
                                     on this tunnel-group to be synchronized on this
                                     multi-chassis peer.";
                            }

                            leaf await-conf {
                                type uint32;
                                description
                                    "The number of static multi-chassis tunnel awaiting
                                     configuration on this tunnel-group to be synchronized on this
                                     multi-chassis peer.";
                            }

                            leaf failed {
                                type uint32;
                                description
                                    "The number of static multi-chassis tunnel failed to install
                                     on this tunnel-group to be synchronized on this
                                     multi-chassis peer.";
                            }

                        } // list tunnel-group

                    } // container mc-ipsec

                    container mc-lag {
                        description "Enter the mc-lag context";

                        leaf oper-state {
                            type enumeration {
                                enum in-service                     { value 0; }
                                enum out-of-service                 { value 1; }
                            }
                            description
                                "Indicates the operational state of this multi-chassis peer
                                 with respect to multi-chassis lag operation.";
                        }

                        list lag {
                            key "lag-name";
                            description "Enter the lag list instance";

                            leaf lag-name {
                                type leafref {
                                    path "../../../../../../lag/lag-name";
                                }
                                description "LAG Name";
                            }

                            leaf oper-source-bmac-lsb {
                                type types-services:bmac-lsb;
                                description "indicates the operational value of last 16-bits of the MAC address used for all the traffic ingressing the MC-Lag links.";
                            }

                            leaf oper-state {
                                type enumeration {
                                    enum not-applic                     { value 0; }
                                    enum active                         { value 1; }
                                    enum standby                        { value 2; }
                                }
                                description "indicates whether this mc-lag is active or standby.";
                            }

                            leaf lacp-id-in-use {
                                type boolean;
                                description "indicates whether or not the mc-lag values (i.e. system-id, system priority and lacp-key) are advertised to the Lacp peer.";
                            }

                            leaf selection-logic {
                                type types-sros:description;
                                description "information about the multi-chassis selection logic.";
                            }

                            leaf config-mismatch-string {
                                type types-sros:description;
                                description "information about the multi-chassis configuration mismatch.";
                            }

                            leaf config-mismatch-flags {
                                type bits {
                                    bit lag-is-not-multi-chassis       { position 0; }
                                    bit local-remote-lag-id-mismatch   { position 1; }
                                    bit lag-selection-criteria-mismatch { position 2; }
                                    bit lag-encapsulation-mismatch     { position 3; }
                                    bit mc-lacp-key-mismatch           { position 4; }
                                    bit mc-system-priority-mismatch    { position 5; }
                                    bit mc-system-id-mismatch          { position 6; }
                                }
                                description "indicates the operational status of the multi-chassis configuration.";
                            }

                        } // list lag

                    } // container mc-lag

                    container mc-ring {
                        description "Enter the mc-ring context";

                        container statistics {
                            description "Enter the statistics context";

                            leaf tx-signalling-msg {
                                type yang:counter32;
                                description "The number of signalling messages transmitted to the peer.";
                            }

                            leaf rx-signalling-msg {
                                type yang:counter32;
                                description "The number of valid signalling messages received from the peer.";
                            }

                            leaf tx-mcs-id-requests {
                                type yang:counter32;
                                description "The number of MCS ID requests transmitted to the peer.";
                            }

                            leaf rx-mcs-id-requests {
                                type yang:counter32;
                                description "The number of valid MCS ID requests received from the peer.";
                            }

                            leaf tx-mcs-id-responses {
                                type yang:counter32;
                                description "The number of MCS ID responses transmitted to the peer.";
                            }

                            leaf rx-mcs-id-responses {
                                type yang:counter32;
                                description "The number of valid MCS ID responses received from the peer.";
                            }

                            leaf tx-ring-exists-requests {
                                type yang:counter32;
                                description "The number of ring-exists requests transmitted to the peer.";
                            }

                            leaf rx-ring-exists-requests {
                                type yang:counter32;
                                description "The number of valid ring-exists requests received from the peer.";
                            }

                            leaf tx-ring-exists-responses {
                                type yang:counter32;
                                description "The number of ring-exists responses transmitted to the peer.";
                            }

                            leaf rx-ring-exists-responses {
                                type yang:counter32;
                                description "The number of valid ring-exists responses received from the peer.";
                            }

                            leaf tx-keep-alive {
                                type yang:counter32;
                                description "The number of keep-alive messages transmitted to the peer.";
                            }

                            leaf rx-keep-alive {
                                type yang:counter32;
                                description "The number of valid keep-alive messages received from the peer.";
                            }

                        } // container statistics

                        list ring {
                            key "sync-tag";
                            description "Enter the ring list instance";

                            leaf sync-tag {
                                type types-sros:named-item;
                                description
                                    "The synchronization tag this ring uses to be synchronized
                                     on this multi-chassis peer.";
                            }

                            leaf oper-state {
                                type enumeration {
                                    enum unknown                        { value 1; }
                                    enum shutdown                       { value 2; }
                                    enum config-error                   { value 3; }
                                    enum no-peer                        { value 4; }
                                    enum connected                      { value 5; }
                                    enum broken                         { value 6; }
                                    enum local-broken                   { value 7; }
                                    enum conflict                       { value 8; }
                                    enum testing-ring                   { value 9; }
                                    enum half-broken                    { value 10; }
                                    enum waiting-for-peer               { value 11; }
                                }
                                description "The operational state of the multi-chassis ring";
                            }

                            leaf failure-reason {
                                type types-sros:display-string {
                                    length "1..80";
                                }
                                description "The reason why the multi-chassis ring is in one of the failed states.";
                            }

                            container in-band-control-path {
                                description "Enter the in-band-control-path context";

                                leaf oper-state {
                                    type types-mcr:ring-oper-state;
                                    description "The operational state of the in-band control connection.";
                                }

                                leaf port-id {
                                    type types-sros:port;
                                    description "The port associated with this ring.";
                                }

                                leaf src-ip {
                                    type types-sros:ipv4-unicast-address;
                                    description "The source address used in the in-band control connection.";
                                }

                                leaf debounce-start {
                                    type yang:date-and-time;
                                    description
                                        "The last time the debounce timer was started after the in-band control
                                         connection transitioned from connected to broken.";
                                }

                                leaf debounce-timeout {
                                    type types-sros:time-interval;
                                    description
                                        "The value of the debounce timer at the time indicated by
                                         debounce-start. Data traffic may have been dropped starting from
                                         debounce-start during the interval indicated by debounce-timeout.";
                                }

                                leaf debounce-guard-time {
                                    type uint32;
                                    units "seconds";
                                    description
                                        "The value of the debounce guard time. If no transitions of the
                                         operational state of the in-band control connection occur during the
                                         debounce guard time, the debounce mechanism is reset.";
                                }

                                leaf controls-path-b {
                                    type boolean;
                                    description "Indicates if the current node controls path-b or not.";
                                }

                            } // container in-band-control-path

                            container oper-path-b {
                                description "Enter the oper-path-b context";

                                leaf wildcard-saps {
                                    type boolean;
                                    description "Include the SAPs starting with a wildcard '*'";
                                }

                                list range {
                                    key "start end";
                                    description "Enter the range list instance";

                                    leaf start {
                                        type uint32 {
                                            range "0..4094";
                                        }
                                        description "The first VLAN in the range.";
                                    }

                                    leaf end {
                                        type uint32 {
                                            range "0..4094";
                                        }
                                        description "The last VLAN in the range.";
                                    }

                                } // list range

                            } // container oper-path-b

                            container oper-path-excl {
                                description "Enter the oper-path-excl context";

                                leaf wildcard-saps {
                                    type boolean;
                                    description "Include the SAPs starting with a wildcard '*'";
                                }

                                list range {
                                    key "start end";
                                    description "Enter the range list instance";

                                    leaf start {
                                        type uint32 {
                                            range "0..4094";
                                        }
                                        description "The first VLAN in the range.";
                                    }

                                    leaf end {
                                        type uint32 {
                                            range "0..4094";
                                        }
                                        description "The last VLAN in the range.";
                                    }

                                } // list range

                            } // container oper-path-excl

                            container statistics {
                                description "Enter the statistics context";

                                leaf tx-saps-changed {
                                    type yang:counter32;
                                    description "The number of SAPS CHANGED messages transmitted to the peer.";
                                }

                                leaf rx-saps-changed {
                                    type yang:counter32;
                                    description "The number of valid SAPS CHANGED messages received from the peer.";
                                }

                                leaf tx-opaque {
                                    type yang:counter32;
                                    description "The number of OPAQUE messages transmitted to the peer.";
                                }

                                leaf rx-opaque {
                                    type yang:counter32;
                                    description
                                        "The number of valid OPAQUE messages received from the peer and delivered
                                         to the multi-chassis ring.";
                                }

                                leaf rx-opaque-no-dest {
                                    type yang:counter32;
                                    description
                                        "The number of valid OPAQUE messages received from the peer for which no
                                         valid destination was found.";
                                }

                            } // container statistics

                            list ring-node {
                                key "name";
                                description "Enter the ring-node list instance";

                                leaf name {
                                    type types-sros:named-item;
                                    description "The name of a multi-chassis ring access node.";
                                }

                                leaf local-oper-state {
                                    type types-mcr:ring-node-oper-state;
                                    description "The operational state of the ring node as monitored by the local chassis.";
                                }

                                leaf remote-oper-state {
                                    type types-mcr:ring-node-oper-state;
                                    description "The operational state of the ring node as monitored by the remote chassis.";
                                }

                                leaf in-use {
                                    type boolean;
                                    description
                                        "Indicates if this ring node is currently used by any subscriber or configured
                                         as ring-node on any SAP.";
                                }

                                leaf failure-reason {
                                    type types-sros:display-string {
                                        length "1..80";
                                    }
                                    description "The reason why the ring-node is in one of the failed states.";
                                }

                                container statistics {
                                    description "Enter the statistics context";

                                    leaf tx-detected {
                                        type yang:counter32;
                                        description "The number of DETECTED RING-NODE signalling messages transmitted by this system.";
                                    }

                                    leaf rx-detected {
                                        type yang:counter32;
                                        description "The number of valid DETECTED RING-NODE signalling messages received from the peer.";
                                    }

                                    leaf tx-detected-ack {
                                        type yang:counter32;
                                        description "The number of DETECTED RING-NODE signalling messages that were acknowledged by this system.";
                                    }

                                    leaf rx-detected-ack {
                                        type yang:counter32;
                                        description "The number of DETECTED RING-NODE signalling messages that were acked by the peer.";
                                    }

                                    leaf tx-rncv-requests {
                                        type yang:counter32;
                                        description "The number of connectivity verification requests transmitted for this ring-node.";
                                    }

                                    leaf rx-rncv-responses {
                                        type yang:counter32;
                                        description "The number of valid connectivity verification responses received for this ring-node.";
                                    }

                                    leaf last-rncv-delay {
                                        type types-sros:time-interval;
                                        description "The round-trip time of the last successful connectivity verification for this ring-node";
                                    }

                                } // container statistics

                            } // list ring-node

                            list debounce-event {
                                key "index";
                                description "Enter the debounce-event list instance";

                                leaf index {
                                    type uint32;
                                    description "A unique value that identifies the debounce event.";
                                }

                                leaf start {
                                    type types-sros:date-time;
                                    description
                                        "The time that the debounce timer was started after the in-band control
                                         connection transitioned from connected to broken.";
                                }

                                leaf debounce-time {
                                    type uint32;
                                    units "seconds";
                                    description "The value of the debounce timer at the start of the debounce event.";
                                }

                                leaf oper-state {
                                    type types-mcr:ring-oper-state;
                                    description "The operational state of the multi-chassis ring after debouncing.";
                                }

                            } // list debounce-event

                        } // list ring

                    } // container mc-ring

                    container wpp {
                        description "Enter the wpp context";

                        list statistics {
                            key "id";
                            description "Enter the statistics list instance";

                            leaf id {
                                type uint32 {
                                    range "0..40";
                                }
                                description "The counter id.";
                            }

                            leaf description {
                                type types-sros:display-string {
                                    length "1..64";
                                }
                                description "Describes the statistic.";
                            }

                            leaf value {
                                type yang:counter32;
                                description "The value of the counter.";
                            }

                        } // list statistics

                    } // container wpp

                } // list peer

            } // container multi-chassis

            container synchronization {
                description "Enter the synchronization context";

                leaf standby-status {
                    type enumeration {
                        enum failed {
                            value -1;
                            description "The problem occurs.";
                        }
                        enum standby {
                            value 3;
                            description "The standby CPM in the redundant pair.";
                        }
                        enum disabled {
                            value 5;
                            description "CPM is not available.";
                        }
                        enum syncing {
                            value 6;
                            description "The redundant pair is syncing.";
                        }
                    }
                    description "Indicates the synchronization status of the standby CPM card.";
                }

                leaf standby-failure {
                    type types-sros:display-string;
                    description "Indicates the reason why a hardware component 'failed'.";
                }

                leaf standby-uptime {
                    type yang:date-and-time;
                    description "The date and time of the last reboot.";
                }

                leaf standby-version {
                    type types-sros:display-string;
                    description
                        "The software product release version number for
                         the software image currently running on this card.";
                }

                leaf failover-time {
                    type types-redundancy:date-and-time-or-never;
                    description
                        "The time when the last redundancy failover occurred
                         causing a switchover from active to standby CPM.";
                }

                leaf failover-reason {
                    type types-sros:description;
                    description
                        "A text string giving an explanation of the cause of
                         the last redundancy failover.";
                }

                leaf sync-status {
                    type enumeration {
                        enum unknown {
                            value 0;
                            description "No synchronization.";
                        }
                        enum config-only {
                            value 1;
                            description "Config only synchronized.";
                        }
                        enum boot-env {
                            value 2;
                            description "All boot environment synchronized.";
                        }
                        enum config-fail {
                            value 3;
                            description "Config synchronize failed.";
                        }
                        enum boot-env-fail {
                            value 4;
                            description "Boot environment synchronize failed.";
                        }
                        enum config-in-progress {
                            value 5;
                            description "Config synchronize in progress.";
                        }
                        enum boot-env-in-progress {
                            value 6;
                            description "Boot environment synchronize in progress.";
                        }
                    }
                    description
                        "The results of the last synchronization operation between
                         the primary and secondary CPMs.";
                }

                leaf config-file-sync-time {
                    type types-redundancy:date-and-time-or-never;
                    description
                        "The time of the last successful synchronization
                         of the configuration files.";
                }

                leaf boot-file-sync-time {
                    type types-redundancy:date-and-time-or-never;
                    description
                        "The time of the last successful synchronization
                         of the boot files.";
                }

                leaf rollback-sync-status {
                    type types-redundancy:sync-status;
                    description
                        "The results of the last rollback synchronization operation
                         between the primary and secondary CPMs.";
                }

                leaf rollback-sync-time {
                    type types-redundancy:date-and-time-or-never;
                    description
                        "The time of the last successful synchronization
                         of the rollback files.";
                }

                leaf cert-file-sync-status {
                    type types-redundancy:sync-status;
                    description
                        "The results of the last certificate synchronization
                         operation between the primary and secondary CPMs.";
                }

                leaf cert-file-sync-time {
                    type types-redundancy:date-and-time-or-never;
                    description
                        "The time of the last successful synchronization
                         of the certificate files.";
                }

            } // container synchronization

            container bgp-evpn {
                description "Enter the bgp-evpn context";

                container ethernet-segment {
                    description "Enter the ethernet-segment context";

                    leaf boot-timer-remaining {
                        type uint32;
                        units "seconds";
                        description
                            "specifies the time remaining for the system to wait after a node
                             reboot before running the BGP EVPN multi-homing DF (designated-forwarder)
                             election algorithm for BGP EVPN services.";
                    }

                } // container ethernet-segment

            } // container bgp-evpn

        } // container redundancy

    } // grouping state-redundancy

}
