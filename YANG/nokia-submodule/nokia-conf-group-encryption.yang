submodule nokia-conf-group-encryption {

    yang-version "1.1";

    belongs-to nokia-conf { prefix "conf"; }

    import nokia-sros-yang-extensions     { prefix "sros-ext"; }
    import nokia-types-sros               { prefix "types-sros"; }

    include nokia-conf-groups;

    sros-ext:sros-major-release "rel26";
    organization "Nokia";
    contact
        "Nokia SR OS Support
         Web: <http://www.nokia.com>";
    description
        "Nokia YANG Data model to configure Group encryption on SR OS based routers.

         Copyright 2016 Nokia. All rights reserved. Reproduction of this document
         is authorized on the condition that the foregoing copyright notice is included.

         This nokia-conf-group-encryption YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping conf-group-encryption {
        container group-encryption {
            description "Enter the group-encryption context";

            leaf group-encryption-label {
                type uint32 {
                    range "32..2047";
                }
                sros-ext:immutable;
                description "Network-wide unique MPLS label for group encryption";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list encryption-keygroup {
                key "id";
                max-elements 127;
                description "Enter the encryption-keygroup list instance";

                leaf id {
                    type uint32 {
                        range "1..127";
                    }
                    description "Encryption key group ID";
                }

                leaf description {
                    type types-sros:description;
                    description "Text description";
                }

                leaf keygroup-name {
                    type types-sros:named-item-64-or-empty;
                    default "";
                    description "Key group name";
                }

                leaf authentication-algorithm {
                    type enumeration {
                        enum sha256                         { value 1; }
                        enum sha512                         { value 2; }
                    }
                    sros-ext:immutable;
                    default "sha256";
                    description "Hashing algorithm used for the authentication function";
                }

                leaf encryption-algorithm {
                    type enumeration {
                        enum aes128                         { value 1; }
                        enum aes256                         { value 2; }
                    }
                    sros-ext:immutable;
                    default "aes128";
                    description "Encryption algorithm for encryption on ESP";
                }

                leaf active-outbound-security-association {
                    type leafref {
                        path "../security-association/security-parameter-index";
                    }
                    description "SPI to use for egressing packets for the key group";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list security-association {
                    key "security-parameter-index";
                    max-elements 4;
                    description "Enter the security-association list instance";

                    leaf security-parameter-index {
                        type uint32 {
                            range "1..1023";
                        }
                        description "Security Parameter Index (SPI)";
                    }

                    leaf authentication-key {
                        type types-sros:encrypted-leaf-hex {
                            length "1..166";
                        }
                        sros-ext:immutable;
                        mandatory true;
                        description "Key used for the authentication algorithm";
                    }

                    leaf encryption-key {
                        type types-sros:encrypted-leaf-hex {
                            length "1..126";
                        }
                        sros-ext:immutable;
                        mandatory true;
                        description "Key used for the encryption algorithm";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list security-association

            } // list encryption-keygroup

        } // container group-encryption

    } // grouping conf-group-encryption

}
