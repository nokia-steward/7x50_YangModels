submodule nokia-state-dms {

    yang-version "1.1";

    belongs-to nokia-state { prefix "state"; }

    import ietf-yang-types                { prefix "yang"; }
    import nokia-sros-yang-extensions     { prefix "sros-ext"; }
    import nokia-types-dms                { prefix "types-dms"; }
    import nokia-types-isa                { prefix "types-isa"; }
    import nokia-types-sros               { prefix "types-sros"; }

    include nokia-state-esa;

    sros-ext:sros-major-release "rel26";
    organization "Nokia";
    contact
        "Nokia SR OS Support
         Web: <http://www.nokia.com>";
    description
        "Nokia YANG Data model with operational state for defender mitigation system on SR OS based routers.

         Copyright 2016 Nokia. All rights reserved. Reproduction of this document
         is authorized on the condition that the foregoing copyright notice is included.

         This nokia-state-dms YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping state-dms-defender-mitigation-system {
        container defender-mitigation-system {
            description "Enter the defender-mitigation-system context";

            list esa {
                key "esa-id vm";
                description "Enter the esa list instance";

                leaf esa-id {
                    type leafref {
                        path "../../../esa/esa-id";
                    }
                    description "Specifies an ESA identifier.";
                }

                leaf vm {
                    type leafref {
                        path "../../../esa[esa-id=current()/../esa-id]/vm/vm-id";
                    }
                    description "Specifies the VM identifier within the ESA.";
                }

                container statistics {
                    description "Enter the statistics context";

                    container to-protected-object {
                        description "Enter the to-protected-object context";

                        container packet-qualifier-discards {
                            description "Enter the packet-qualifier-discards context";

                            container invalid-protected-object {
                                description "Enter the invalid-protected-object context";

                                leaf octets {
                                    type yang:counter64;
                                    units "bytes";
                                    description
                                        "Number of bytes discarded in L3/L4 packet qualification checks by the ESA NIC
                                         that did not match a Protected Object.";
                                }

                                leaf packets {
                                    type yang:counter64;
                                    units "packets";
                                    description
                                        "Number of packets discarded in L3/L4 packet qualification checks by the ESA NIC
                                         that did not match a Protected Object.";
                                }

                            } // container invalid-protected-object

                            container protected-object {
                                description "Enter the protected-object context";

                                leaf octets {
                                    type yang:counter64;
                                    units "bytes";
                                    description "Number of bytes discarded in L3/L4 packet qualification checks by the ESA NIC.";
                                }

                                leaf packets {
                                    type yang:counter64;
                                    units "packets";
                                    description "Number of packets discarded in L3/L4 packet qualification checks by the ESA NIC.";
                                }

                            } // container protected-object

                        } // container packet-qualifier-discards

                        container receive {
                            description "Enter the receive context";

                            leaf octets {
                                type yang:counter64;
                                units "bytes";
                                description "Number of bytes received by the esa-vm (not including packet-qualifier discards).";
                            }

                            leaf packets {
                                type yang:counter64;
                                units "packets";
                                description "Number of packets received by the esa-vm (not including packet-qualifier discards).";
                            }

                        } // container receive

                        container discards {
                            description "Enter the discards context";

                            container invalid-protected-object {
                                description "Enter the invalid-protected-object context";

                                leaf octets {
                                    type yang:counter64;
                                    units "bytes";
                                    description "Number of bytes discarded for received traffic that did not match a Protected Object.";
                                }

                                leaf packets {
                                    type yang:counter64;
                                    units "packets";
                                    description "Number of packets discarded for received traffic that did not match a Protected Object.";
                                }

                            } // container invalid-protected-object

                            container protected-object {
                                description "Enter the protected-object context";

                                leaf octets {
                                    type yang:counter64;
                                    units "bytes";
                                    description "Number of bytes discarded for received traffic for all Protected Objects.";
                                }

                                leaf packets {
                                    type yang:counter64;
                                    units "packets";
                                    description "Number of packets discarded for received traffic for all Protected Object.";
                                }

                            } // container protected-object

                        } // container discards

                        container generated {
                            description "Enter the generated context";

                            leaf octets {
                                type yang:counter64;
                                units "bytes";
                                description "Number of bytes for packets generated towards a Protected Object.";
                            }

                            leaf packets {
                                type yang:counter64;
                                units "packets";
                                description "Number of packets generated towards a Protected Object.";
                            }

                        } // container generated

                        container transmit {
                            description "Enter the transmit context";

                            leaf octets {
                                type yang:counter64;
                                units "bytes";
                                description "Number of bytes transmitted to the clean port.";
                            }

                            leaf packets {
                                type yang:counter64;
                                units "packets";
                                description "Number of packets transmitted to the clean port.";
                            }

                        } // container transmit

                    } // container to-protected-object

                    container from-protected-object {
                        description "Enter the from-protected-object context";

                        container packet-qualifier-discards {
                            description "Enter the packet-qualifier-discards context";

                            container invalid-protected-object {
                                description "Enter the invalid-protected-object context";

                                leaf octets {
                                    type yang:counter64;
                                    units "bytes";
                                    description
                                        "Number of bytes discarded in L3/L4 packet qualification checks by the ESA NIC
                                         that did not match a Protected Object.";
                                }

                                leaf packets {
                                    type yang:counter64;
                                    units "packets";
                                    description
                                        "Number of packets discarded in L3/L4 packet qualification checks by the ESA NIC
                                         that did not match a Protected Object.";
                                }

                            } // container invalid-protected-object

                            container protected-object {
                                description "Enter the protected-object context";

                                leaf octets {
                                    type yang:counter64;
                                    units "bytes";
                                    description "Number of bytes discarded in L3/L4 packet qualification checks by the ESA NIC.";
                                }

                                leaf packets {
                                    type yang:counter64;
                                    units "packets";
                                    description "Number of packets discarded in L3/L4 packet qualification checks by the ESA NIC.";
                                }

                            } // container protected-object

                        } // container packet-qualifier-discards

                        container receive {
                            description "Enter the receive context";

                            leaf octets {
                                type yang:counter64;
                                units "bytes";
                                description "Number of bytes received by the esa-vm (not including packet-qualifier discards).";
                            }

                            leaf packets {
                                type yang:counter64;
                                units "packets";
                                description "Number of packets received by the esa-vm (not including packet-qualifier discards).";
                            }

                        } // container receive

                        container discards {
                            description "Enter the discards context";

                            container invalid-protected-object {
                                description "Enter the invalid-protected-object context";

                                leaf octets {
                                    type yang:counter64;
                                    units "bytes";
                                    description "Number of bytes discarded for received traffic that did not match a Protected Object.";
                                }

                                leaf packets {
                                    type yang:counter64;
                                    units "packets";
                                    description "Number of packets discarded for received traffic that did not match a Protected Object.";
                                }

                            } // container invalid-protected-object

                            container protected-object {
                                description "Enter the protected-object context";

                                leaf octets {
                                    type yang:counter64;
                                    units "bytes";
                                    description "Number of bytes discarded for received traffic for all Protected Objects.";
                                }

                                leaf packets {
                                    type yang:counter64;
                                    units "packets";
                                    description "Number of packets discarded for received traffic for all Protected Object.";
                                }

                            } // container protected-object

                        } // container discards

                        container generated {
                            description "Enter the generated context";

                            leaf octets {
                                type yang:counter64;
                                units "bytes";
                                description "Number of bytes for packets generated away from a Protected Object.";
                            }

                            leaf packets {
                                type yang:counter64;
                                units "packets";
                                description "Number of packets generated away from a Protected Object.";
                            }

                        } // container generated

                        container transmit {
                            description "Enter the transmit context";

                            leaf octets {
                                type yang:counter64;
                                units "bytes";
                                description "Number of bytes transmitted to the dirty port.";
                            }

                            leaf packets {
                                type yang:counter64;
                                units "packets";
                                description "Number of packets transmitted to the dirty port.";
                            }

                        } // container transmit

                    } // container from-protected-object

                } // container statistics

                container status {
                    description "Enter the status context";

                    container resources {
                        description "Enter the resources context";

                        container tracked-sources {
                            description "Enter the tracked-sources context";

                            leaf current {
                                type yang:gauge32;
                                description "The current number of tracked source records in-use on the DMS esa-vm(s).";
                            }

                            leaf average {
                                type yang:gauge32;
                                description "The average number of tracked source records in-use on the DMS esa-vm(s) within the last 60 minutes.";
                            }

                            leaf peak {
                                type yang:gauge32;
                                description "The peak number of tracked source records in-use on the DMS esa-vm(s) since system startup.";
                            }

                            leaf usage-status {
                                type types-dms:resource-usage-status-type;
                                description "The level of source records in-use on the DMS esa-vm(s) considering the overall system limit.";
                            }

                        } // container tracked-sources

                        container flows {
                            description "Enter the flows context";

                            leaf current {
                                type yang:gauge32;
                                units "flows";
                                description "The current number of flow records in-use on the DMS esa-vm(s).";
                            }

                            leaf average {
                                type yang:gauge32;
                                units "flows";
                                description "The average number of flow records in-use on the DMS esa-vm(s) within the last 60 minutes.";
                            }

                            leaf peak {
                                type yang:gauge32;
                                units "flows";
                                description "The peak number of flow records in-use on the DMS esa-vm(s) since system startup.";
                            }

                            leaf usage-status {
                                type types-dms:resource-usage-status-type;
                                description "The level of flow records in-use on the DMS esa-vm(s) considering the overall system limit.";
                            }

                        } // container flows

                        container sessions {
                            description "Enter the sessions context";

                            leaf current {
                                type yang:gauge32;
                                units "flows";
                                description "The current number of session records in-use on the DMS esa-vm(s).";
                            }

                            leaf average {
                                type yang:gauge32;
                                units "flows";
                                description "The average number of session records in-use on the DMS esa-vm(s) within the last 60 minutes.";
                            }

                            leaf peak {
                                type yang:gauge32;
                                units "flows";
                                description "The peak number of session records in-use on the DMS esa-vm(s) since system startup.";
                            }

                            leaf usage-status {
                                type types-dms:resource-usage-status-type;
                                description "The level of session records in-use on the DMS esa-vm(s) considering the overall system limit.";
                            }

                        } // container sessions

                    } // container resources

                    container traffic {
                        description "Enter the traffic context";

                        container bit-rate {
                            description "Enter the bit-rate context";

                            leaf current {
                                type yang:gauge32;
                                units "megabps";
                                description "The current traffic bit-rate in megabits per second (mbps) incoming to the DMS esa-vm(s).";
                            }

                            leaf average {
                                type yang:gauge32;
                                units "megabps";
                                description "The average traffic bit-rate in megabits per second (mbps) incoming to the DMS esa-vm(s) within the last 60 minutes.";
                            }

                            leaf peak {
                                type yang:gauge32;
                                units "megabps";
                                description "The peak traffic bit-rate in megabits per second (mbps) incoming to the DMS esa-vm(s) since system startup.";
                            }

                        } // container bit-rate

                        container packet-rate {
                            description "Enter the packet-rate context";

                            leaf current {
                                type yang:gauge32;
                                units "packets per second";
                                description "The current number of packets per second incoming to the DMS esa-vm(s).";
                            }

                            leaf average {
                                type yang:gauge32;
                                units "packets per second";
                                description "The average number of packets per second incoming to the DMS esa-vm(s) within the last 60 minutes.";
                            }

                            leaf peak {
                                type yang:gauge32;
                                units "packets per second";
                                description "The peak number of packets per second incoming to the DMS esa-vm(s) since system startup.";
                            }

                        } // container packet-rate

                        container source-setup-rate {
                            description "Enter the source-setup-rate context";

                            leaf current {
                                type yang:gauge32;
                                units "records per second";
                                description "The current rate of tracked source IP setups per second on the DMS esa-vm(s).";
                            }

                            leaf average {
                                type yang:gauge32;
                                units "records per second";
                                description "The average number of tracked source IP setups per second on the DMS esa-vm(s) within the last 60 minutes.";
                            }

                            leaf peak {
                                type yang:gauge32;
                                units "records per second";
                                description "The peak number of tracked source IP setups per second on the DMS esa-vm(s) since system startup.";
                            }

                        } // container source-setup-rate

                        container flow-setup-rate {
                            description "Enter the flow-setup-rate context";

                            leaf current {
                                type yang:gauge32;
                                units "flows per second";
                                description "The current rate of flow setups per second on the DMS esa-vm(s).";
                            }

                            leaf average {
                                type yang:gauge32;
                                units "flows per second";
                                description "The average rate of flow setups per second on the DMS esa-vm(s) within the last 60 minutes.";
                            }

                            leaf peak {
                                type yang:gauge32;
                                units "flows per second";
                                description "The peak rate of flow setups per second on the DMS esa-vm(s) since system startup.";
                            }

                        } // container flow-setup-rate

                        container session-setup-rate {
                            description "Enter the session-setup-rate context";

                            leaf current {
                                type yang:gauge32;
                                units "flows per second";
                                description "The current rate of session setups per second on the DMS esa-vm(s).";
                            }

                            leaf average {
                                type yang:gauge32;
                                units "flows per second";
                                description "The average rate of session setups per second on the DMS esa-vm(s) within the last 60 minutes.";
                            }

                            leaf peak {
                                type yang:gauge32;
                                units "flows per second";
                                description "The peak rate of session setups per second on the DMS esa-vm(s) since system startup.";
                            }

                        } // container session-setup-rate

                    } // container traffic

                } // container status

            } // list esa

            container summary {
                description "Enter the summary context";

                container statistics {
                    description "Enter the statistics context";

                    container to-protected-object {
                        description "Enter the to-protected-object context";

                        container packet-qualifier-discards {
                            description "Enter the packet-qualifier-discards context";

                            container invalid-protected-object {
                                description "Enter the invalid-protected-object context";

                                leaf octets {
                                    type yang:counter64;
                                    units "bytes";
                                    description
                                        "Number of bytes discarded in L3/L4 packet qualification checks by the ESA NIC
                                         that did not match a Protected Object.";
                                }

                                leaf packets {
                                    type yang:counter64;
                                    units "packets";
                                    description
                                        "Number of packets discarded in L3/L4 packet qualification checks by the ESA NIC
                                         that did not match a Protected Object.";
                                }

                            } // container invalid-protected-object

                            container protected-object {
                                description "Enter the protected-object context";

                                leaf octets {
                                    type yang:counter64;
                                    units "bytes";
                                    description "Number of bytes discarded in L3/L4 packet qualification checks by the ESA NIC.";
                                }

                                leaf packets {
                                    type yang:counter64;
                                    units "packets";
                                    description "Number of packets discarded in L3/L4 packet qualification checks by the ESA NIC.";
                                }

                            } // container protected-object

                        } // container packet-qualifier-discards

                        container receive {
                            description "Enter the receive context";

                            leaf octets {
                                type yang:counter64;
                                units "bytes";
                                description "Number of bytes received by the esa-vm (not including packet-qualifier discards).";
                            }

                            leaf packets {
                                type yang:counter64;
                                units "packets";
                                description "Number of packets received by the esa-vm (not including packet-qualifier discards).";
                            }

                        } // container receive

                        container discards {
                            description "Enter the discards context";

                            container invalid-protected-object {
                                description "Enter the invalid-protected-object context";

                                leaf octets {
                                    type yang:counter64;
                                    units "bytes";
                                    description "Number of bytes discarded for received traffic that did not match a Protected Object.";
                                }

                                leaf packets {
                                    type yang:counter64;
                                    units "packets";
                                    description "Number of packets discarded for received traffic that did not match a Protected Object.";
                                }

                            } // container invalid-protected-object

                            container protected-object {
                                description "Enter the protected-object context";

                                leaf octets {
                                    type yang:counter64;
                                    units "bytes";
                                    description "Number of bytes discarded for received traffic for all Protected Objects.";
                                }

                                leaf packets {
                                    type yang:counter64;
                                    units "packets";
                                    description "Number of packets discarded for received traffic for all Protected Object.";
                                }

                            } // container protected-object

                        } // container discards

                        container generated {
                            description "Enter the generated context";

                            leaf octets {
                                type yang:counter64;
                                units "bytes";
                                description "Number of bytes for packets generated towards a Protected Object.";
                            }

                            leaf packets {
                                type yang:counter64;
                                units "packets";
                                description "Number of packets generated towards a Protected Object.";
                            }

                        } // container generated

                        container transmit {
                            description "Enter the transmit context";

                            leaf octets {
                                type yang:counter64;
                                units "bytes";
                                description "Number of bytes transmitted to the clean port.";
                            }

                            leaf packets {
                                type yang:counter64;
                                units "packets";
                                description "Number of packets transmitted to the clean port.";
                            }

                        } // container transmit

                    } // container to-protected-object

                    container from-protected-object {
                        description "Enter the from-protected-object context";

                        container packet-qualifier-discards {
                            description "Enter the packet-qualifier-discards context";

                            container invalid-protected-object {
                                description "Enter the invalid-protected-object context";

                                leaf octets {
                                    type yang:counter64;
                                    units "bytes";
                                    description
                                        "Number of bytes discarded in L3/L4 packet qualification checks by the ESA NIC
                                         that did not match a Protected Object.";
                                }

                                leaf packets {
                                    type yang:counter64;
                                    units "packets";
                                    description
                                        "Number of packets discarded in L3/L4 packet qualification checks by the ESA NIC
                                         that did not match a Protected Object.";
                                }

                            } // container invalid-protected-object

                            container protected-object {
                                description "Enter the protected-object context";

                                leaf octets {
                                    type yang:counter64;
                                    units "bytes";
                                    description "Number of bytes discarded in L3/L4 packet qualification checks by the ESA NIC.";
                                }

                                leaf packets {
                                    type yang:counter64;
                                    units "packets";
                                    description "Number of packets discarded in L3/L4 packet qualification checks by the ESA NIC.";
                                }

                            } // container protected-object

                        } // container packet-qualifier-discards

                        container receive {
                            description "Enter the receive context";

                            leaf octets {
                                type yang:counter64;
                                units "bytes";
                                description "Number of bytes received by the esa-vm (not including packet-qualifier discards).";
                            }

                            leaf packets {
                                type yang:counter64;
                                units "packets";
                                description "Number of packets received by the esa-vm (not including packet-qualifier discards).";
                            }

                        } // container receive

                        container discards {
                            description "Enter the discards context";

                            container invalid-protected-object {
                                description "Enter the invalid-protected-object context";

                                leaf octets {
                                    type yang:counter64;
                                    units "bytes";
                                    description "Number of bytes discarded for received traffic that did not match a Protected Object.";
                                }

                                leaf packets {
                                    type yang:counter64;
                                    units "packets";
                                    description "Number of packets discarded for received traffic that did not match a Protected Object.";
                                }

                            } // container invalid-protected-object

                            container protected-object {
                                description "Enter the protected-object context";

                                leaf octets {
                                    type yang:counter64;
                                    units "bytes";
                                    description "Number of bytes discarded for received traffic for all Protected Objects.";
                                }

                                leaf packets {
                                    type yang:counter64;
                                    units "packets";
                                    description "Number of packets discarded for received traffic for all Protected Object.";
                                }

                            } // container protected-object

                        } // container discards

                        container generated {
                            description "Enter the generated context";

                            leaf octets {
                                type yang:counter64;
                                units "bytes";
                                description "Number of bytes for packets generated away from a Protected Object.";
                            }

                            leaf packets {
                                type yang:counter64;
                                units "packets";
                                description "Number of packets generated away from a Protected Object.";
                            }

                        } // container generated

                        container transmit {
                            description "Enter the transmit context";

                            leaf octets {
                                type yang:counter64;
                                units "bytes";
                                description "Number of bytes transmitted to the dirty port.";
                            }

                            leaf packets {
                                type yang:counter64;
                                units "packets";
                                description "Number of packets transmitted to the dirty port.";
                            }

                        } // container transmit

                    } // container from-protected-object

                } // container statistics

                container status {
                    description "Enter the status context";

                    container resources {
                        description "Enter the resources context";

                        container tracked-sources {
                            description "Enter the tracked-sources context";

                            leaf current {
                                type yang:gauge32;
                                description "The current number of tracked source records in-use on the DMS esa-vm(s).";
                            }

                            leaf average {
                                type yang:gauge32;
                                description "The average number of tracked source records in-use on the DMS esa-vm(s) within the last 60 minutes.";
                            }

                            leaf peak {
                                type yang:gauge32;
                                description "The peak number of tracked source records in-use on the DMS esa-vm(s) since system startup.";
                            }

                            leaf usage-status {
                                type types-dms:resource-usage-status-type;
                                description "The level of source records in-use on the DMS esa-vm(s) considering the overall system limit.";
                            }

                        } // container tracked-sources

                        container flows {
                            description "Enter the flows context";

                            leaf current {
                                type yang:gauge32;
                                units "flows";
                                description "The current number of flow records in-use on the DMS esa-vm(s).";
                            }

                            leaf average {
                                type yang:gauge32;
                                units "flows";
                                description "The average number of flow records in-use on the DMS esa-vm(s) within the last 60 minutes.";
                            }

                            leaf peak {
                                type yang:gauge32;
                                units "flows";
                                description "The peak number of flow records in-use on the DMS esa-vm(s) since system startup.";
                            }

                            leaf usage-status {
                                type types-dms:resource-usage-status-type;
                                description "The level of flow records in-use on the DMS esa-vm(s) considering the overall system limit.";
                            }

                        } // container flows

                        container sessions {
                            description "Enter the sessions context";

                            leaf current {
                                type yang:gauge32;
                                units "flows";
                                description "The current number of session records in-use on the DMS esa-vm(s).";
                            }

                            leaf average {
                                type yang:gauge32;
                                units "flows";
                                description "The average number of session records in-use on the DMS esa-vm(s) within the last 60 minutes.";
                            }

                            leaf peak {
                                type yang:gauge32;
                                units "flows";
                                description "The peak number of session records in-use on the DMS esa-vm(s) since system startup.";
                            }

                            leaf usage-status {
                                type types-dms:resource-usage-status-type;
                                description "The level of session records in-use on the DMS esa-vm(s) considering the overall system limit.";
                            }

                        } // container sessions

                    } // container resources

                    container traffic {
                        description "Enter the traffic context";

                        container bit-rate {
                            description "Enter the bit-rate context";

                            leaf current {
                                type yang:gauge32;
                                units "megabps";
                                description "The current traffic bit-rate in megabits per second (mbps) incoming to the DMS esa-vm(s).";
                            }

                            leaf average {
                                type yang:gauge32;
                                units "megabps";
                                description "The average traffic bit-rate in megabits per second (mbps) incoming to the DMS esa-vm(s) within the last 60 minutes.";
                            }

                            leaf peak {
                                type yang:gauge32;
                                units "megabps";
                                description "The peak traffic bit-rate in megabits per second (mbps) incoming to the DMS esa-vm(s) since system startup.";
                            }

                        } // container bit-rate

                        container packet-rate {
                            description "Enter the packet-rate context";

                            leaf current {
                                type yang:gauge32;
                                units "packets per second";
                                description "The current number of packets per second incoming to the DMS esa-vm(s).";
                            }

                            leaf average {
                                type yang:gauge32;
                                units "packets per second";
                                description "The average number of packets per second incoming to the DMS esa-vm(s) within the last 60 minutes.";
                            }

                            leaf peak {
                                type yang:gauge32;
                                units "packets per second";
                                description "The peak number of packets per second incoming to the DMS esa-vm(s) since system startup.";
                            }

                        } // container packet-rate

                        container source-setup-rate {
                            description "Enter the source-setup-rate context";

                            leaf current {
                                type yang:gauge32;
                                units "records per second";
                                description "The current rate of tracked source IP setups per second on the DMS esa-vm(s).";
                            }

                            leaf average {
                                type yang:gauge32;
                                units "records per second";
                                description "The average number of tracked source IP setups per second on the DMS esa-vm(s) within the last 60 minutes.";
                            }

                            leaf peak {
                                type yang:gauge32;
                                units "records per second";
                                description "The peak number of tracked source IP setups per second on the DMS esa-vm(s) since system startup.";
                            }

                        } // container source-setup-rate

                        container flow-setup-rate {
                            description "Enter the flow-setup-rate context";

                            leaf current {
                                type yang:gauge32;
                                units "flows per second";
                                description "The current rate of flow setups per second on the DMS esa-vm(s).";
                            }

                            leaf average {
                                type yang:gauge32;
                                units "flows per second";
                                description "The average rate of flow setups per second on the DMS esa-vm(s) within the last 60 minutes.";
                            }

                            leaf peak {
                                type yang:gauge32;
                                units "flows per second";
                                description "The peak rate of flow setups per second on the DMS esa-vm(s) since system startup.";
                            }

                        } // container flow-setup-rate

                        container session-setup-rate {
                            description "Enter the session-setup-rate context";

                            leaf current {
                                type yang:gauge32;
                                units "flows per second";
                                description "The current rate of session setups per second on the DMS esa-vm(s).";
                            }

                            leaf average {
                                type yang:gauge32;
                                units "flows per second";
                                description "The average rate of session setups per second on the DMS esa-vm(s) within the last 60 minutes.";
                            }

                            leaf peak {
                                type yang:gauge32;
                                units "flows per second";
                                description "The peak rate of session setups per second on the DMS esa-vm(s) since system startup.";
                            }

                        } // container session-setup-rate

                    } // container traffic

                } // container status

            } // container summary

            container advanced-countermeasures-group {
                description "Enter the advanced-countermeasures-group context";

                list esa {
                    key "esa-id vm";
                    description "Enter the esa list instance";

                    leaf esa-id {
                        type leafref {
                            path "../../../../esa/esa-id";
                        }
                        description "Specifies an ESA identifier.";
                    }

                    leaf vm {
                        type leafref {
                            path "../../../../esa[esa-id=current()/../esa-id]/vm/vm-id";
                        }
                        description "Specifies the VM identifier within the ESA.";
                    }

                    leaf oper-state {
                        type types-sros:oper-state;
                        description "The operational state of the DMS esa-vm.";
                    }

                    leaf oper-flags {
                        type types-dms:esa-vm-oper-flags-type;
                        description "The different failure conditions that affect the operating status of the DMS esa-vm.";
                    }

                } // list esa

                list isa {
                    key "mda-id";
                    description "Enter the isa list instance";

                    leaf mda-id {
                        type types-isa:slot-mda;
                        description "Specifies an MDA/ISA identifier <card slot number>/<mda slot number>";
                    }

                    leaf oper-state {
                        type types-sros:oper-state;
                        description "The operational state of the DMS isa.";
                    }

                    leaf oper-flags {
                        type types-dms:isa-oper-flags-type;
                        description "The different failure conditions that affect the operating status of the DMS isa.";
                    }

                } // list isa

            } // container advanced-countermeasures-group

            container genome-list-import {
                description "Enter the genome-list-import context";

                leaf oper-state {
                    type types-sros:oper-state;
                    description "The operational state of the DMS genome-list-import module.";
                }

                leaf oper-flags {
                    type types-dms:genome-list-import-conditions-type;
                    description "The different conditions that affect the operating status of genome-list-import.";
                }

                leaf in-progress {
                    type boolean;
                    description "Indicates 'true' if there is a genome list import attempt currently in progress.";
                }

                leaf file-version {
                    type uint32;
                    description "The JSON schema version of the file from the last successful genome list import.";
                }

                leaf last-attempt-time {
                    type yang:date-and-time;
                    description
                        "The most recent time of an attempted genome list import.  When a genome list import is successful
                         last-attempt-time and last-success-time will be the same and in-progress will be 'false'.";
                }

                leaf last-success-time {
                    type yang:date-and-time;
                    description
                        "The most recent time of a successful genome list import.  When a genome list import is successful
                         last-attempt-time and last-success-time will be the same and in-progress will be 'false'.";
                }

                leaf next-attempt-time {
                    type yang:date-and-time;
                    description "The next time that a genome list import will be attempted.";
                }

                leaf refresh-failure-oper-flags {
                    type types-dms:genome-list-import-conditions-type;
                    description "The different conditions that affect the refreshing of a genome-list-import.";
                }

                container genome-lists {
                    description "Enter the genome-lists context";

                    leaf expected {
                        type yang:gauge32;
                        description "The number of genome-lists that the DMS software expects to find in the genome list import.";
                    }

                    leaf missing {
                        type yang:gauge32;
                        description
                            "The number of expected genome-lists that were not found in the genome list import.  If non-zero, this
                             indicates a potential error condition.  PO pre-filter configurations against missing genome-lists do
                             not operate as expected.";
                    }

                    leaf unsupported {
                        type yang:gauge32;
                        description "The number of unexpected extra genome-lists in the genome list import that were ignored.";
                    }

                } // container genome-lists

                container ipv4 {
                    description "Enter the ipv4 context";

                    leaf addresses {
                        type yang:gauge32;
                        description "The number of exact IPv4 addresses contained in the last successful genome list import.";
                    }

                    leaf prefixes {
                        type yang:gauge32;
                        description "The number of IPv4 prefixes contained in the last successful genome list import.";
                    }

                    leaf errors {
                        type yang:gauge32;
                        description "The number of IPv4 errors contained in the last successful genome list import.";
                    }

                    container limits {
                        description "Enter the limits context";

                        leaf addresses {
                            type yang:gauge32;
                            description "The maximum number of IPv4 addresses that can be imported from the genome list file.";
                        }

                        leaf prefixes {
                            type yang:gauge32;
                            description "The maximum number of IPv4 prefixes that can be imported from the genome list file.";
                        }

                    } // container limits

                } // container ipv4

                container ipv6 {
                    description "Enter the ipv6 context";

                    leaf addresses {
                        type yang:gauge32;
                        description "The number of exact IPv6 addresses contained in the last successful genome list import.";
                    }

                    leaf prefixes {
                        type yang:gauge32;
                        description "The number of IPv6 prefixes contained in the last successful genome list import.";
                    }

                    leaf errors {
                        type yang:gauge32;
                        description "The number of IPv6 errors contained in the last successful genome list import.";
                    }

                    container limits {
                        description "Enter the limits context";

                        leaf addresses {
                            type yang:gauge32;
                            description "The maximum number of IPv6 addresses that can be imported from the genome list file.";
                        }

                        leaf prefixes {
                            type yang:gauge32;
                            description "The maximum number of IPv6 prefixes that can be imported from the genome list file.";
                        }

                    } // container limits

                } // container ipv6

            } // container genome-list-import

            container user-list-import {
                description "Enter the user-list-import context";

                leaf oper-state {
                    type types-sros:oper-state;
                    description "The operational state of the DMS user-list-import module.";
                }

                leaf oper-flags {
                    type types-dms:user-list-import-conditions-type;
                    description "The different conditions that affect the operating status of user-list-import.";
                }

                leaf in-progress {
                    type boolean;
                    description "Indicates 'true' if there is a user list import attempt currently in progress.";
                }

                leaf file-version {
                    type uint32;
                    description "The JSON schema version of the file from the last successful user list import.";
                }

                leaf last-attempt-time {
                    type yang:date-and-time;
                    description
                        "The most recent time of an attempted user list import.  When a user list import is successful
                         last-attempt-time and last-success-time will be the same and in-progress will be 'false'.";
                }

                leaf last-success-time {
                    type yang:date-and-time;
                    description
                        "The most recent time of a successful user list import.  When a user list import is successful
                         last-attempt-time and last-success-time will be the same and in-progress will be 'false'.";
                }

                leaf next-attempt-time {
                    type yang:date-and-time;
                    description "The next time that a user list import will be attempted.";
                }

                leaf refresh-failure-oper-flags {
                    type types-dms:user-list-import-conditions-type;
                    description "The different conditions that affect the refreshing of a user-list-import.";
                }

                container user-lists {
                    description "Enter the user-lists context";

                    leaf dns-lists {
                        type yang:gauge32;
                        description "The number of DNS domain lists that the DMS software found in the last successful user list import.";
                    }

                    leaf dns-lists-total-strings {
                        type yang:gauge32;
                        description "The total number of strings in all DNS domain lists that the DMS software found in the last successful user list import.";
                    }

                    container tls {
                        description "Enter the tls context";

                        leaf fingerprint-lists {
                            type yang:gauge32;
                            description "The number of TLS fingerprint lists that the DMS software found in the last successful user list import.";
                        }

                        leaf total-ja3-fingerprints {
                            type yang:gauge32;
                            description "The total number of JA3 fingerprints in all TLS fingerprint lists that the DMS software found in the last successful user list import.";
                        }

                        leaf total-ja4-tcp-fingerprints {
                            type yang:gauge32;
                            description "The total number of JA4 tcp fingerprints in all TLS fingerprint lists that the DMS software found in the last successful user list import.";
                        }

                    } // container tls

                } // container user-lists

            } // container user-list-import


            list protected-object {
                key "id";
                description "Enter the protected-object list instance";

                leaf id {
                    type uint32 {
                        range "1..4294967295";
                    }
                    description "Uniquely identifies the Protected Object.";
                }

                list esa {
                    key "esa-id vm";
                    description "Enter the esa list instance";

                    leaf esa-id {
                        type leafref {
                            path "../../../../esa/esa-id";
                        }
                        description "Specifies an ESA identifier.";
                    }

                    leaf vm {
                        type leafref {
                            path "../../../../esa[esa-id=current()/../esa-id]/vm/vm-id";
                        }
                        description "Specifies the VM identifier within the ESA.";
                    }

                    container statistics {
                        description "Enter the statistics context";

                        container to-protected-object {
                            description "Enter the to-protected-object context";

                            leaf tracked-sources-created {
                                type yang:counter64;
                                description
                                    "The all-time number of tracked source records created for this Protected
                                     Object for traffic in the to-protected-object direction on the DMS
                                     esa-vm(s) since system startup.";
                            }

                            leaf sessions-created {
                                type yang:counter64;
                                units "flows";
                                description
                                    "The all-time number of sessions created for this Protected Object
                                     for traffic in the inbound (to-protected-object) direction on the DMS
                                     esa-vm(s) since system startup.";
                            }

                            leaf flows-created {
                                type yang:counter64;
                                units "flows";
                                description
                                    "The all-time number of flow records created for this Protected
                                     Object for traffic in the to-protected-object direction on the DMS
                                     esa-vm(s) since system startup.";
                            }

                            container packet-qualifier-discards {
                                description "Enter the packet-qualifier-discards context";

                                container ipv4 {
                                    description "Enter the ipv4 context";

                                    container errors {
                                        description "Enter the errors context";

                                        leaf octets {
                                            type yang:counter64;
                                            units "bytes";
                                            description "Number of bytes discarded due to IPv4 packet errors for a Protected Object.";
                                        }

                                        leaf packets {
                                            type yang:counter64;
                                            units "packets";
                                            description "Number of packets discarded due to IPv4 packet errors for a Protected Object.";
                                        }

                                    } // container errors

                                    container tcp-errors {
                                        description "Enter the tcp-errors context";

                                        leaf octets {
                                            type yang:counter64;
                                            units "bytes";
                                            description "Number of bytes discarded due to IPv4 TCP packet errors for a Protected Object.";
                                        }

                                        leaf packets {
                                            type yang:counter64;
                                            units "packets";
                                            description "Number of packets discarded due to IPv4 TCP packet errors for a Protected Object.";
                                        }

                                    } // container tcp-errors

                                    container udp-errors {
                                        description "Enter the udp-errors context";

                                        leaf octets {
                                            type yang:counter64;
                                            units "bytes";
                                            description "Number of bytes discarded due to IPv4 UDP packet errors for a Protected Object.";
                                        }

                                        leaf packets {
                                            type yang:counter64;
                                            units "packets";
                                            description "Number of packets discarded due to IPv4 UDP packet errors for a Protected Object.";
                                        }

                                    } // container udp-errors

                                } // container ipv4

                                container ipv6 {
                                    description "Enter the ipv6 context";

                                    container errors {
                                        description "Enter the errors context";

                                        leaf octets {
                                            type yang:counter64;
                                            units "bytes";
                                            description "Number of bytes of discarded IPv6 packets with errors for a Protected Object.";
                                        }

                                        leaf packets {
                                            type yang:counter64;
                                            units "packets";
                                            description "Number of discarded IPv6 packets with errors for a Protected Object.";
                                        }

                                    } // container errors

                                    container tcp-errors {
                                        description "Enter the tcp-errors context";

                                        leaf octets {
                                            type yang:counter64;
                                            units "bytes";
                                            description "Number of bytes discarded due to IPv6 TCP packet errors for a Protected Object.";
                                        }

                                        leaf packets {
                                            type yang:counter64;
                                            units "packets";
                                            description "Number of packets discarded due to IPv6 TCP packet errors for a Protected Object.";
                                        }

                                    } // container tcp-errors

                                    container udp-errors {
                                        description "Enter the udp-errors context";

                                        leaf octets {
                                            type yang:counter64;
                                            units "bytes";
                                            description "Number of bytes discarded due to IPv6 UDP packet errors for a Protected Object.";
                                        }

                                        leaf packets {
                                            type yang:counter64;
                                            units "packets";
                                            description "Number of packets discarded due to IPv6 UDP packet errors for a Protected Object.";
                                        }

                                    } // container udp-errors

                                } // container ipv6

                            } // container packet-qualifier-discards

                            container receive {
                                description "Enter the receive context";

                                leaf octets {
                                    type yang:counter64;
                                    units "bytes";
                                    description
                                        "Number of bytes received for a Protected Object.  This does not include
                                         NIC discards";
                                }

                                leaf packets {
                                    type yang:counter64;
                                    units "packets";
                                    description
                                        "Number of packets received for a Protected Object.  This does not include
                                         NIC discards";
                                }

                            } // container receive

                            container bypass {
                                description "Enter the bypass context";

                                container pre-filter {
                                    description "Enter the pre-filter context";

                                    leaf octets {
                                        type yang:counter64;
                                        units "bytes";
                                        description "Number of bytes that bypassed mitigation-rules by the pre-filter for a Protected Object.";
                                    }

                                    leaf packets {
                                        type yang:counter64;
                                        units "packets";
                                        description "Number of packets that bypassed mitigation-rules by the pre-filter for a Protected Object.";
                                    }

                                } // container pre-filter

                                container ip-fragments {
                                    description "Enter the ip-fragments context";

                                    leaf octets {
                                        type yang:counter64;
                                        units "bytes";
                                        description "Number of bytes of IP subsequent fragments that bypassed mitigation-rules for a Protected Object.";
                                    }

                                    leaf packets {
                                        type yang:counter64;
                                        units "packets";
                                        description "Number of packets of IP subsequent fragments that bypassed mitigation-rules for a Protected Object.";
                                    }

                                } // container ip-fragments

                                container countermeasure {
                                    description "Enter the countermeasure context";

                                    leaf octets {
                                        type yang:counter64;
                                        units "bytes";
                                        description "Number of bytes of packets that bypassed countermeasures for a Protected Object.";
                                    }

                                    leaf packets {
                                        type yang:counter64;
                                        units "packets";
                                        description "Number of packets that bypassed countermeasures for a Protected Object.";
                                    }

                                } // container countermeasure

                            } // container bypass

                            container discards {
                                description "Enter the discards context";

                                container malformed {
                                    description "Enter the malformed context";

                                    leaf octets {
                                        type yang:counter64;
                                        units "bytes";
                                        description "Number of bytes discarded in malformed packets for a Protected Object.";
                                    }

                                    leaf packets {
                                        type yang:counter64;
                                        units "packets";
                                        description "Number of malformed packets discarded for a Protected Object.";
                                    }

                                } // container malformed

                                container checksum-verification {
                                    description "Enter the checksum-verification context";

                                    container ipv4 {
                                        description "Enter the ipv4 context";

                                        container tcp-errors {
                                            description "Enter the tcp-errors context";

                                            leaf octets {
                                                type yang:counter64;
                                                units "bytes";
                                                description "Number of bytes discarded due to IPv4 TCP checksum errors for a Protected Object.";
                                            }

                                            leaf packets {
                                                type yang:counter64;
                                                units "packets";
                                                description "Number of packets discarded due to IPv4 TCP checksum errors for a Protected Object.";
                                            }

                                        } // container tcp-errors

                                        container udp-errors {
                                            description "Enter the udp-errors context";

                                            leaf octets {
                                                type yang:counter64;
                                                units "bytes";
                                                description "Number of bytes discarded due to IPv4 UDP checksum errors for a Protected Object.";
                                            }

                                            leaf packets {
                                                type yang:counter64;
                                                units "packets";
                                                description "Number of packets discarded due to IPv4 UDP checksum errors for a Protected Object.";
                                            }

                                        } // container udp-errors

                                    } // container ipv4

                                    container ipv6 {
                                        description "Enter the ipv6 context";

                                        container tcp-errors {
                                            description "Enter the tcp-errors context";

                                            leaf octets {
                                                type yang:counter64;
                                                units "bytes";
                                                description "Number of bytes discarded due to IPv6 TCP checksum errors for a Protected Object.";
                                            }

                                            leaf packets {
                                                type yang:counter64;
                                                units "packets";
                                                description "Number of packets discarded due to IPv6 TCP checksum errors for a Protected Object.";
                                            }

                                        } // container tcp-errors

                                        container udp-errors {
                                            description "Enter the udp-errors context";

                                            leaf octets {
                                                type yang:counter64;
                                                units "bytes";
                                                description "Number of bytes discarded due to IPv6 UDP checksum errors for a Protected Object.";
                                            }

                                            leaf packets {
                                                type yang:counter64;
                                                units "packets";
                                                description "Number of packets discarded due to IPv6 UDP checksum errors for a Protected Object.";
                                            }

                                        } // container udp-errors

                                    } // container ipv6

                                } // container checksum-verification

                                container ip-fragments {
                                    description "Enter the ip-fragments context";

                                    leaf octets {
                                        type yang:counter64;
                                        units "bytes";
                                        description
                                            "Number of bytes of IP subsequent fragments that were discarded because the initial
                                             fragment was discarded for a Protected Object.";
                                    }

                                    leaf packets {
                                        type yang:counter64;
                                        units "packets";
                                        description
                                            "Number of packets of IP subsequent fragments that were discarded because the initial
                                             fragment was discarded for a Protected Object.";
                                    }

                                } // container ip-fragments

                                container pre-filter {
                                    description "Enter the pre-filter context";

                                    leaf octets {
                                        type yang:counter64;
                                        units "bytes";
                                        description "Number of bytes discarded by the pre-filter for a Protected Object.";
                                    }

                                    leaf packets {
                                        type yang:counter64;
                                        units "packets";
                                        description "Number of packets discarded by the pre-filter for a Protected Object.";
                                    }

                                } // container pre-filter

                                container source-limit {
                                    description "Enter the source-limit context";

                                    leaf octets {
                                        type yang:counter64;
                                        units "bytes";
                                        description "Number of bytes discarded for a new source exceeding source limit for a Protected Object.";
                                    }

                                    leaf packets {
                                        type yang:counter64;
                                        units "packets";
                                        description "Number of packets discarded for a new source exceeding source limit for a Protected Object.";
                                    }

                                } // container source-limit

                                container source-exhaust {
                                    description "Enter the source-exhaust context";

                                    leaf octets {
                                        type yang:counter64;
                                        units "bytes";
                                        description "Number of bytes discarded for a new source exhausting source store for a Protected Object.";
                                    }

                                    leaf packets {
                                        type yang:counter64;
                                        units "packets";
                                        description "Number of packets discarded for a new source exhausting source store for a Protected Object.";
                                    }

                                } // container source-exhaust

                                container source-dynamic-block {
                                    description "Enter the source-dynamic-block context";

                                    leaf octets {
                                        type yang:counter64;
                                        units "bytes";
                                        description "Number of bytes discarded for a tracked-source in the dynamic-block state for a Protected Object.";
                                    }

                                    leaf packets {
                                        type yang:counter64;
                                        units "packets";
                                        description "Number of packets discarded for a tracked-source in the dynamic-block state for a Protected Object.";
                                    }

                                } // container source-dynamic-block

                                container flow-limit {
                                    description "Enter the flow-limit context";

                                    leaf octets {
                                        type yang:counter64;
                                        units "bytes";
                                        description "Number of bytes discarded for a new flow exceeding flow limit for a Protected Object.";
                                    }

                                    leaf packets {
                                        type yang:counter64;
                                        units "packets";
                                        description "Number of packets discarded for a new flow exceeding flow limit for a Protected Object.";
                                    }

                                } // container flow-limit

                                container flow-exhaust {
                                    description "Enter the flow-exhaust context";

                                    leaf octets {
                                        type yang:counter64;
                                        units "bytes";
                                        description "Number of bytes discarded for a new flow exhausting flow store for a Protected Object.";
                                    }

                                    leaf packets {
                                        type yang:counter64;
                                        units "packets";
                                        description "Number of packets discarded for a new flow exhausting flow store for a Protected Object.";
                                    }

                                } // container flow-exhaust

                                container session-limit {
                                    description "Enter the session-limit context";

                                    leaf octets {
                                        type yang:counter64;
                                        units "bytes";
                                        description "Number of bytes discarded for a new session exceeding session limit for a Protected Object.";
                                    }

                                    leaf packets {
                                        type yang:counter64;
                                        units "packets";
                                        description "Number of packets discarded for a new session exceeding flow limit for a Protected Object.";
                                    }

                                } // container session-limit

                                container session-exhaust {
                                    description "Enter the session-exhaust context";

                                    leaf octets {
                                        type yang:counter64;
                                        units "bytes";
                                        description "Number of bytes discarded for a new session exhausting session store for a Protected Object.";
                                    }

                                    leaf packets {
                                        type yang:counter64;
                                        units "packets";
                                        description "Number of packets discarded for a new session exhausting session store for a Protected Object.";
                                    }

                                } // container session-exhaust


                                container mitigation-rules {
                                    description "Enter the mitigation-rules context";

                                    leaf octets {
                                        type yang:counter64;
                                        units "bytes";
                                        description
                                            "Number of bytes discarded by mitigation-rule entries for a Protected Object
                                             in the to-protected-object direction.";
                                    }

                                    leaf packets {
                                        type yang:counter64;
                                        units "packets";
                                        description
                                            "Number of packets discarded by mitigation-rule entries for a Protected Object
                                             in the to-protected-object direction.";
                                    }

                                    container client-authentication {
                                        description "Enter the client-authentication context";

                                        leaf octets {
                                            type yang:counter64;
                                            units "bytes";
                                            description "Number of bytes discarded by Client Authentication in mitigation-rule entries for the Protected Object.";
                                        }

                                        leaf packets {
                                            type yang:counter64;
                                            units "packets";
                                            description "Number of packets discarded by Client Authentication in mitigation-rule entries for the Protected Object.";
                                        }

                                    } // container client-authentication

                                } // container mitigation-rules


                            } // container discards

                            container generated {
                                description "Enter the generated context";

                                container tcp-reset {
                                    description "Enter the tcp-reset context";

                                    leaf octets {
                                        type yang:counter64;
                                        units "bytes";
                                        description "Number of bytes for TCP Resets generated towards a Protected Object.";
                                    }

                                    leaf packets {
                                        type yang:counter64;
                                        units "packets";
                                        description "Number of packets for TCP Resets generated towards a Protected Object.";
                                    }

                                } // container tcp-reset

                            } // container generated

                            container transmit {
                                description "Enter the transmit context";

                                leaf octets {
                                    type yang:counter64;
                                    units "bytes";
                                    description "Number of bytes transmitted for a Protected Object.";
                                }

                                leaf packets {
                                    type yang:counter64;
                                    units "packets";
                                    description "Number of packets transmitted for a Protected Object.";
                                }

                            } // container transmit

                        } // container to-protected-object

                        container from-protected-object {
                            description "Enter the from-protected-object context";

                            leaf tracked-sources-created {
                                type yang:counter64;
                                description
                                    "The all-time number of tracked source records created for this Protected
                                     Object for traffic in the outbound (from-protected-object) direction on
                                     the DMS esa-vm(s) since system startup.";
                            }

                            leaf flows-created {
                                type yang:counter64;
                                units "flows";
                                description
                                    "The all-time number of flow records created for this Protected
                                     Object for traffic in the outbound (from-protected-object direction on the DMS
                                     esa-vm(s) since system startup.";
                            }

                            container packet-qualifier-discards {
                                description "Enter the packet-qualifier-discards context";

                                container ipv4 {
                                    description "Enter the ipv4 context";

                                    container errors {
                                        description "Enter the errors context";

                                        leaf octets {
                                            type yang:counter64;
                                            units "bytes";
                                            description "Number of bytes discarded due to IPv4 errors for a Protected Object.";
                                        }

                                        leaf packets {
                                            type yang:counter64;
                                            units "packets";
                                            description "Number of packets discarded due to IPv4 errors for a Protected Object.";
                                        }

                                    } // container errors

                                    container tcp-errors {
                                        description "Enter the tcp-errors context";

                                        leaf octets {
                                            type yang:counter64;
                                            units "bytes";
                                            description "Number of bytes discarded due to IPv4 TCP packet errors for a Protected Object.";
                                        }

                                        leaf packets {
                                            type yang:counter64;
                                            units "packets";
                                            description "Number of packets discarded due to IPv4 TCP packet errors for a Protected Object.";
                                        }

                                    } // container tcp-errors

                                    container udp-errors {
                                        description "Enter the udp-errors context";

                                        leaf octets {
                                            type yang:counter64;
                                            units "bytes";
                                            description "Number of bytes discarded due to IPv4 UDP packet errors for a Protected Object.";
                                        }

                                        leaf packets {
                                            type yang:counter64;
                                            units "packets";
                                            description "Number of packets discarded due to IPv4 UDP packet errors for a Protected Object.";
                                        }

                                    } // container udp-errors

                                } // container ipv4

                                container ipv6 {
                                    description "Enter the ipv6 context";

                                    container errors {
                                        description "Enter the errors context";

                                        leaf octets {
                                            type yang:counter64;
                                            units "bytes";
                                            description "Number of bytes of discarded IPv6 packets with errors for a Protected Object.";
                                        }

                                        leaf packets {
                                            type yang:counter64;
                                            units "packets";
                                            description "Number of discarded IPv6 packets with errors for a Protected Object.";
                                        }

                                    } // container errors

                                    container tcp-errors {
                                        description "Enter the tcp-errors context";

                                        leaf octets {
                                            type yang:counter64;
                                            units "bytes";
                                            description "Number of bytes discarded due to IPv6 TCP packet errors for a Protected Object.";
                                        }

                                        leaf packets {
                                            type yang:counter64;
                                            units "packets";
                                            description "Number of packets discarded due to IPv6 TCP packet errors for a Protected Object.";
                                        }

                                    } // container tcp-errors

                                    container udp-errors {
                                        description "Enter the udp-errors context";

                                        leaf octets {
                                            type yang:counter64;
                                            units "bytes";
                                            description "Number of bytes discarded due to IPv6 UDP packet errors for a Protected Object.";
                                        }

                                        leaf packets {
                                            type yang:counter64;
                                            units "packets";
                                            description "Number of packets discarded due to IPv6 UDP packet errors for a Protected Object.";
                                        }

                                    } // container udp-errors

                                } // container ipv6

                            } // container packet-qualifier-discards

                            container receive {
                                description "Enter the receive context";

                                leaf octets {
                                    type yang:counter64;
                                    units "bytes";
                                    description
                                        "Number of bytes received for a Protected Object.  This does not include
                                         NIC discards";
                                }

                                leaf packets {
                                    type yang:counter64;
                                    units "packets";
                                    description
                                        "Number of packets received for a Protected Object.  This does not include
                                         NIC discards";
                                }

                            } // container receive

                            container bypass {
                                description "Enter the bypass context";

                                container pre-filter {
                                    description "Enter the pre-filter context";

                                    leaf octets {
                                        type yang:counter64;
                                        units "bytes";
                                        description "Number of bytes that bypassed outbound mitigation-rules by the pre-filter for a Protected Object.";
                                    }

                                    leaf packets {
                                        type yang:counter64;
                                        units "packets";
                                        description "Number of packets that bypassed outbound mitigation-rules by the pre-filter for a Protected Object.";
                                    }

                                } // container pre-filter

                                container ip-fragments {
                                    description "Enter the ip-fragments context";

                                    leaf octets {
                                        type yang:counter64;
                                        units "bytes";
                                        description "Number of bytes of IP subsequent fragments that bypassed outbound mitigation-rules for a Protected Object.";
                                    }

                                    leaf packets {
                                        type yang:counter64;
                                        units "packets";
                                        description "Number of packets of IP subsequent fragments that bypassed outbound mitigation-rules for a Protected Object.";
                                    }

                                } // container ip-fragments

                                container countermeasure {
                                    description "Enter the countermeasure context";

                                    leaf octets {
                                        type yang:counter64;
                                        units "bytes";
                                        description "Number of bytes of packets that bypassed outbound countermeasures for a Protected Object.";
                                    }

                                    leaf packets {
                                        type yang:counter64;
                                        units "packets";
                                        description "Number of packets that bypassed outbound countermeasures for a Protected Object.";
                                    }

                                } // container countermeasure

                            } // container bypass

                            container discards {
                                description "Enter the discards context";

                                container malformed {
                                    description "Enter the malformed context";

                                    leaf octets {
                                        type yang:counter64;
                                        units "bytes";
                                        description "Number of bytes discarded in malformed outbound packets for a Protected Object.";
                                    }

                                    leaf packets {
                                        type yang:counter64;
                                        units "packets";
                                        description "Number of malformed outbound packets discarded for a Protected Object.";
                                    }

                                } // container malformed

                                container checksum-verification {
                                    description "Enter the checksum-verification context";

                                    container ipv4 {
                                        description "Enter the ipv4 context";

                                        container tcp-errors {
                                            description "Enter the tcp-errors context";

                                            leaf octets {
                                                type yang:counter64;
                                                units "bytes";
                                                description "Number of bytes discarded due to IPv4 TCP checksum errors for a Protected Object.";
                                            }

                                            leaf packets {
                                                type yang:counter64;
                                                units "packets";
                                                description "Number of packets discarded due to IPv4 TCP checksum errors for a Protected Object.";
                                            }

                                        } // container tcp-errors

                                        container udp-errors {
                                            description "Enter the udp-errors context";

                                            leaf octets {
                                                type yang:counter64;
                                                units "bytes";
                                                description "Number of bytes discarded due to IPv4 UDP checksum errors for a Protected Object.";
                                            }

                                            leaf packets {
                                                type yang:counter64;
                                                units "packets";
                                                description "Number of packets discarded due to IPv4 UDP checksum errors for a Protected Object.";
                                            }

                                        } // container udp-errors

                                    } // container ipv4

                                    container ipv6 {
                                        description "Enter the ipv6 context";

                                        container tcp-errors {
                                            description "Enter the tcp-errors context";

                                            leaf octets {
                                                type yang:counter64;
                                                units "bytes";
                                                description "Number of bytes discarded due to IPv6 TCP checksum errors for a Protected Object.";
                                            }

                                            leaf packets {
                                                type yang:counter64;
                                                units "packets";
                                                description "Number of packets discarded due to IPv6 TCP checksum errors for a Protected Object.";
                                            }

                                        } // container tcp-errors

                                        container udp-errors {
                                            description "Enter the udp-errors context";

                                            leaf octets {
                                                type yang:counter64;
                                                units "bytes";
                                                description "Number of bytes discarded due to IPv6 UDP checksum errors for a Protected Object.";
                                            }

                                            leaf packets {
                                                type yang:counter64;
                                                units "packets";
                                                description "Number of packets discarded due to IPv6 UDP checksum errors for a Protected Object.";
                                            }

                                        } // container udp-errors

                                    } // container ipv6

                                } // container checksum-verification

                                container ip-fragments {
                                    description "Enter the ip-fragments context";

                                    leaf octets {
                                        type yang:counter64;
                                        units "bytes";
                                        description
                                            "Number of bytes of IP subsequent fragments that were discarded because the initial
                                             fragment was discarded for a Protected Object.";
                                    }

                                    leaf packets {
                                        type yang:counter64;
                                        units "packets";
                                        description
                                            "Number of packets of IP subsequent fragments that were discarded because the initial
                                             fragment was discarded for a Protected Object.";
                                    }

                                } // container ip-fragments

                                container pre-filter {
                                    description "Enter the pre-filter context";

                                    leaf octets {
                                        type yang:counter64;
                                        units "bytes";
                                        description "Number of bytes discarded by the outbound pre-filter for a Protected Object.";
                                    }

                                    leaf packets {
                                        type yang:counter64;
                                        units "packets";
                                        description "Number of packets discarded by the outbound pre-filter for a Protected Object.";
                                    }

                                } // container pre-filter

                                container source-limit {
                                    description "Enter the source-limit context";

                                    leaf octets {
                                        type yang:counter64;
                                        units "bytes";
                                        description "Number of bytes discarded for a new outbound source exceeding source limit for a Protected Object.";
                                    }

                                    leaf packets {
                                        type yang:counter64;
                                        units "packets";
                                        description "Number of packets discarded for a new outbound source exceeding source limit for a Protected Object.";
                                    }

                                } // container source-limit

                                container source-exhaust {
                                    description "Enter the source-exhaust context";

                                    leaf octets {
                                        type yang:counter64;
                                        units "bytes";
                                        description "Number of bytes discarded for a new outbound source exhausting source store for a Protected Object.";
                                    }

                                    leaf packets {
                                        type yang:counter64;
                                        units "packets";
                                        description "Number of packets discarded for a new outbound source exhausting source store for a Protected Object.";
                                    }

                                } // container source-exhaust




                                container mitigation-rules {
                                    description "Enter the mitigation-rules context";

                                    leaf octets {
                                        type yang:counter64;
                                        units "bytes";
                                        description
                                            "Number of bytes discarded by mitigation-rule entries for a Protected Object
                                             in the from-protected-object direction.";
                                    }

                                    leaf packets {
                                        type yang:counter64;
                                        units "packets";
                                        description
                                            "Number of packets discarded by mitigation-rule entries for a Protected Object
                                             in the from-protected-object direction.";
                                    }

                                } // container mitigation-rules


                            } // container discards

                            container generated {
                                description "Enter the generated context";

                                container mitigation-rules {
                                    description "Enter the mitigation-rules context";

                                    container client-authentication {
                                        description "Enter the client-authentication context";

                                        leaf octets {
                                            type yang:counter64;
                                            units "bytes";
                                            description "Number of bytes generated by Client Authentication actions of mitigation-rules for the Protected Object.";
                                        }

                                        leaf packets {
                                            type yang:counter64;
                                            units "packets";
                                            description "Number of packets generated by Client Authentication actions of mitigation-rules for the Protected Object.";
                                        }

                                    } // container client-authentication

                                } // container mitigation-rules

                            } // container generated

                            container transmit {
                                description "Enter the transmit context";

                                leaf octets {
                                    type yang:counter64;
                                    units "bytes";
                                    description "Number of bytes transmitted for a Protected Object.";
                                }

                                leaf packets {
                                    type yang:counter64;
                                    units "packets";
                                    description "Number of packets transmitted for a Protected Object.";
                                }

                            } // container transmit

                        } // container from-protected-object

                    } // container statistics

                    container status {
                        description "Enter the status context";

                        container resources {
                            description "Enter the resources context";

                            container tracked-sources {
                                description "Enter the tracked-sources context";

                                leaf current {
                                    type yang:gauge32;
                                    description
                                        "The current number of inbound tracked source records in-use for this
                                         Protected Object on the DMS esa-vm(s).";
                                }

                                leaf peak {
                                    type yang:gauge32;
                                    description
                                        "The peak number of inbound tracked source records in-use for this
                                         Protected Object on the DMS esa-vm(s) since system startup.";
                                }

                                leaf usage-status {
                                    type types-dms:resource-usage-status-type;
                                    description
                                        "The level of inbound source records in-use for this Protected Object
                                         on the DMS esa-vm(s) considering the configured tracked-source-limit.";
                                }

                            } // container tracked-sources

                            container sessions {
                                description "Enter the sessions context";

                                leaf current {
                                    type yang:gauge32;
                                    units "flows";
                                    description
                                        "The current number of session records initiated in the inbound direction
                                         in-use for this Protected Object on the DMS esa-vm(s).";
                                }

                                leaf peak {
                                    type yang:gauge32;
                                    units "flows";
                                    description
                                        "The peak number of session records initiated in the inbound direction
                                         in-use for this Protected Object on the DMS esa-vm(s) since system startup.";
                                }

                                leaf usage-status {
                                    type types-dms:resource-usage-status-type;
                                    description
                                        "The level of session records initiated in the inbound direction in-use for
                                         this Protected Object on the DMS esa-vm(s) considering the configured
                                         tracked-session-limit.";
                                }

                            } // container sessions

                            container flows {
                                description "Enter the flows context";

                                leaf current {
                                    type yang:gauge32;
                                    units "flows";
                                    description
                                        "The current number of inbound flow records in-use for this Protected
                                         Object on the DMS esa-vm(s).";
                                }

                                leaf peak {
                                    type yang:gauge32;
                                    units "flows";
                                    description
                                        "The peak number of inbound flow records in-use for this Protected
                                         Object on the DMS esa-vm(s) since system startup.";
                                }

                                leaf usage-status {
                                    type types-dms:resource-usage-status-type;
                                    description
                                        "The level of inbound flow records in-use for this Protected Object
                                         on the DMS esa-vm(s) considering the configured tracked-flow-limit.";
                                }

                            } // container flows

                            container outbound {
                                description "Enter the outbound context";

                                container tracked-sources {
                                    description "Enter the tracked-sources context";

                                    leaf current {
                                        type yang:gauge32;
                                        description
                                            "The current number of outbound tracked source records in-use for this
                                             Protected Object on the DMS esa-vm(s).";
                                    }

                                    leaf peak {
                                        type yang:gauge32;
                                        description
                                            "The peak number of outbound tracked source records in-use for this
                                             Protected Object on the DMS esa-vm(s) since system startup.";
                                    }

                                    leaf usage-status {
                                        type types-dms:resource-usage-status-type;
                                        description
                                            "The level of outbound source records in-use for this Protected Object on
                                             the DMS esa-vm(s) considering the configured outbound tracked-source-limit.";
                                    }

                                } // container tracked-sources


                            } // container outbound

                        } // container resources

                    } // container status

                } // list esa

                container summary {
                    description "Enter the summary context";

                    container statistics {
                        description "Enter the statistics context";

                        container to-protected-object {
                            description "Enter the to-protected-object context";

                            leaf tracked-sources-created {
                                type yang:counter64;
                                description
                                    "The all-time number of tracked source records created for this Protected
                                     Object for traffic in the to-protected-object direction on the DMS
                                     esa-vm(s) since system startup.";
                            }

                            leaf sessions-created {
                                type yang:counter64;
                                units "flows";
                                description
                                    "The all-time number of sessions created for this Protected Object
                                     for traffic in the inbound (to-protected-object) direction on the DMS
                                     esa-vm(s) since system startup.";
                            }

                            leaf flows-created {
                                type yang:counter64;
                                units "flows";
                                description
                                    "The all-time number of flow records created for this Protected
                                     Object for traffic in the to-protected-object direction on the DMS
                                     esa-vm(s) since system startup.";
                            }

                            container packet-qualifier-discards {
                                description "Enter the packet-qualifier-discards context";

                                container ipv4 {
                                    description "Enter the ipv4 context";

                                    container errors {
                                        description "Enter the errors context";

                                        leaf octets {
                                            type yang:counter64;
                                            units "bytes";
                                            description "Number of bytes discarded due to IPv4 packet errors for a Protected Object.";
                                        }

                                        leaf packets {
                                            type yang:counter64;
                                            units "packets";
                                            description "Number of packets discarded due to IPv4 packet errors for a Protected Object.";
                                        }

                                    } // container errors

                                    container tcp-errors {
                                        description "Enter the tcp-errors context";

                                        leaf octets {
                                            type yang:counter64;
                                            units "bytes";
                                            description "Number of bytes discarded due to IPv4 TCP packet errors for a Protected Object.";
                                        }

                                        leaf packets {
                                            type yang:counter64;
                                            units "packets";
                                            description "Number of packets discarded due to IPv4 TCP packet errors for a Protected Object.";
                                        }

                                    } // container tcp-errors

                                    container udp-errors {
                                        description "Enter the udp-errors context";

                                        leaf octets {
                                            type yang:counter64;
                                            units "bytes";
                                            description "Number of bytes discarded due to IPv4 UDP packet errors for a Protected Object.";
                                        }

                                        leaf packets {
                                            type yang:counter64;
                                            units "packets";
                                            description "Number of packets discarded due to IPv4 UDP packet errors for a Protected Object.";
                                        }

                                    } // container udp-errors

                                } // container ipv4

                                container ipv6 {
                                    description "Enter the ipv6 context";

                                    container errors {
                                        description "Enter the errors context";

                                        leaf octets {
                                            type yang:counter64;
                                            units "bytes";
                                            description "Number of bytes of discarded IPv6 packets with errors for a Protected Object.";
                                        }

                                        leaf packets {
                                            type yang:counter64;
                                            units "packets";
                                            description "Number of discarded IPv6 packets with errors for a Protected Object.";
                                        }

                                    } // container errors

                                    container tcp-errors {
                                        description "Enter the tcp-errors context";

                                        leaf octets {
                                            type yang:counter64;
                                            units "bytes";
                                            description "Number of bytes discarded due to IPv6 TCP packet errors for a Protected Object.";
                                        }

                                        leaf packets {
                                            type yang:counter64;
                                            units "packets";
                                            description "Number of packets discarded due to IPv6 TCP packet errors for a Protected Object.";
                                        }

                                    } // container tcp-errors

                                    container udp-errors {
                                        description "Enter the udp-errors context";

                                        leaf octets {
                                            type yang:counter64;
                                            units "bytes";
                                            description "Number of bytes discarded due to IPv6 UDP packet errors for a Protected Object.";
                                        }

                                        leaf packets {
                                            type yang:counter64;
                                            units "packets";
                                            description "Number of packets discarded due to IPv6 UDP packet errors for a Protected Object.";
                                        }

                                    } // container udp-errors

                                } // container ipv6

                            } // container packet-qualifier-discards

                            container receive {
                                description "Enter the receive context";

                                leaf octets {
                                    type yang:counter64;
                                    units "bytes";
                                    description
                                        "Number of bytes received for a Protected Object.  This does not include
                                         NIC discards";
                                }

                                leaf packets {
                                    type yang:counter64;
                                    units "packets";
                                    description
                                        "Number of packets received for a Protected Object.  This does not include
                                         NIC discards";
                                }

                            } // container receive

                            container bypass {
                                description "Enter the bypass context";

                                container pre-filter {
                                    description "Enter the pre-filter context";

                                    leaf octets {
                                        type yang:counter64;
                                        units "bytes";
                                        description "Number of bytes that bypassed mitigation-rules by the pre-filter for a Protected Object.";
                                    }

                                    leaf packets {
                                        type yang:counter64;
                                        units "packets";
                                        description "Number of packets that bypassed mitigation-rules by the pre-filter for a Protected Object.";
                                    }

                                } // container pre-filter

                                container ip-fragments {
                                    description "Enter the ip-fragments context";

                                    leaf octets {
                                        type yang:counter64;
                                        units "bytes";
                                        description "Number of bytes of IP subsequent fragments that bypassed mitigation-rules for a Protected Object.";
                                    }

                                    leaf packets {
                                        type yang:counter64;
                                        units "packets";
                                        description "Number of packets of IP subsequent fragments that bypassed mitigation-rules for a Protected Object.";
                                    }

                                } // container ip-fragments

                                container countermeasure {
                                    description "Enter the countermeasure context";

                                    leaf octets {
                                        type yang:counter64;
                                        units "bytes";
                                        description "Number of bytes of packets that bypassed countermeasures for a Protected Object.";
                                    }

                                    leaf packets {
                                        type yang:counter64;
                                        units "packets";
                                        description "Number of packets that bypassed countermeasures for a Protected Object.";
                                    }

                                } // container countermeasure

                            } // container bypass

                            container discards {
                                description "Enter the discards context";

                                container malformed {
                                    description "Enter the malformed context";

                                    leaf octets {
                                        type yang:counter64;
                                        units "bytes";
                                        description "Number of bytes discarded in malformed packets for a Protected Object.";
                                    }

                                    leaf packets {
                                        type yang:counter64;
                                        units "packets";
                                        description "Number of malformed packets discarded for a Protected Object.";
                                    }

                                } // container malformed

                                container checksum-verification {
                                    description "Enter the checksum-verification context";

                                    container ipv4 {
                                        description "Enter the ipv4 context";

                                        container tcp-errors {
                                            description "Enter the tcp-errors context";

                                            leaf octets {
                                                type yang:counter64;
                                                units "bytes";
                                                description "Number of bytes discarded due to IPv4 TCP checksum errors for a Protected Object.";
                                            }

                                            leaf packets {
                                                type yang:counter64;
                                                units "packets";
                                                description "Number of packets discarded due to IPv4 TCP checksum errors for a Protected Object.";
                                            }

                                        } // container tcp-errors

                                        container udp-errors {
                                            description "Enter the udp-errors context";

                                            leaf octets {
                                                type yang:counter64;
                                                units "bytes";
                                                description "Number of bytes discarded due to IPv4 UDP checksum errors for a Protected Object.";
                                            }

                                            leaf packets {
                                                type yang:counter64;
                                                units "packets";
                                                description "Number of packets discarded due to IPv4 UDP checksum errors for a Protected Object.";
                                            }

                                        } // container udp-errors

                                    } // container ipv4

                                    container ipv6 {
                                        description "Enter the ipv6 context";

                                        container tcp-errors {
                                            description "Enter the tcp-errors context";

                                            leaf octets {
                                                type yang:counter64;
                                                units "bytes";
                                                description "Number of bytes discarded due to IPv6 TCP checksum errors for a Protected Object.";
                                            }

                                            leaf packets {
                                                type yang:counter64;
                                                units "packets";
                                                description "Number of packets discarded due to IPv6 TCP checksum errors for a Protected Object.";
                                            }

                                        } // container tcp-errors

                                        container udp-errors {
                                            description "Enter the udp-errors context";

                                            leaf octets {
                                                type yang:counter64;
                                                units "bytes";
                                                description "Number of bytes discarded due to IPv6 UDP checksum errors for a Protected Object.";
                                            }

                                            leaf packets {
                                                type yang:counter64;
                                                units "packets";
                                                description "Number of packets discarded due to IPv6 UDP checksum errors for a Protected Object.";
                                            }

                                        } // container udp-errors

                                    } // container ipv6

                                } // container checksum-verification

                                container ip-fragments {
                                    description "Enter the ip-fragments context";

                                    leaf octets {
                                        type yang:counter64;
                                        units "bytes";
                                        description
                                            "Number of bytes of IP subsequent fragments that were discarded because the initial
                                             fragment was discarded for a Protected Object.";
                                    }

                                    leaf packets {
                                        type yang:counter64;
                                        units "packets";
                                        description
                                            "Number of packets of IP subsequent fragments that were discarded because the initial
                                             fragment was discarded for a Protected Object.";
                                    }

                                } // container ip-fragments

                                container pre-filter {
                                    description "Enter the pre-filter context";

                                    leaf octets {
                                        type yang:counter64;
                                        units "bytes";
                                        description "Number of bytes discarded by the pre-filter for a Protected Object.";
                                    }

                                    leaf packets {
                                        type yang:counter64;
                                        units "packets";
                                        description "Number of packets discarded by the pre-filter for a Protected Object.";
                                    }

                                } // container pre-filter

                                container source-limit {
                                    description "Enter the source-limit context";

                                    leaf octets {
                                        type yang:counter64;
                                        units "bytes";
                                        description "Number of bytes discarded for a new source exceeding source limit for a Protected Object.";
                                    }

                                    leaf packets {
                                        type yang:counter64;
                                        units "packets";
                                        description "Number of packets discarded for a new source exceeding source limit for a Protected Object.";
                                    }

                                } // container source-limit

                                container source-exhaust {
                                    description "Enter the source-exhaust context";

                                    leaf octets {
                                        type yang:counter64;
                                        units "bytes";
                                        description "Number of bytes discarded for a new source exhausting source store for a Protected Object.";
                                    }

                                    leaf packets {
                                        type yang:counter64;
                                        units "packets";
                                        description "Number of packets discarded for a new source exhausting source store for a Protected Object.";
                                    }

                                } // container source-exhaust

                                container source-dynamic-block {
                                    description "Enter the source-dynamic-block context";

                                    leaf octets {
                                        type yang:counter64;
                                        units "bytes";
                                        description "Number of bytes discarded for a tracked-source in the dynamic-block state for a Protected Object.";
                                    }

                                    leaf packets {
                                        type yang:counter64;
                                        units "packets";
                                        description "Number of packets discarded for a tracked-source in the dynamic-block state for a Protected Object.";
                                    }

                                } // container source-dynamic-block

                                container flow-limit {
                                    description "Enter the flow-limit context";

                                    leaf octets {
                                        type yang:counter64;
                                        units "bytes";
                                        description "Number of bytes discarded for a new flow exceeding flow limit for a Protected Object.";
                                    }

                                    leaf packets {
                                        type yang:counter64;
                                        units "packets";
                                        description "Number of packets discarded for a new flow exceeding flow limit for a Protected Object.";
                                    }

                                } // container flow-limit

                                container flow-exhaust {
                                    description "Enter the flow-exhaust context";

                                    leaf octets {
                                        type yang:counter64;
                                        units "bytes";
                                        description "Number of bytes discarded for a new flow exhausting flow store for a Protected Object.";
                                    }

                                    leaf packets {
                                        type yang:counter64;
                                        units "packets";
                                        description "Number of packets discarded for a new flow exhausting flow store for a Protected Object.";
                                    }

                                } // container flow-exhaust

                                container session-limit {
                                    description "Enter the session-limit context";

                                    leaf octets {
                                        type yang:counter64;
                                        units "bytes";
                                        description "Number of bytes discarded for a new session exceeding session limit for a Protected Object.";
                                    }

                                    leaf packets {
                                        type yang:counter64;
                                        units "packets";
                                        description "Number of packets discarded for a new session exceeding flow limit for a Protected Object.";
                                    }

                                } // container session-limit

                                container session-exhaust {
                                    description "Enter the session-exhaust context";

                                    leaf octets {
                                        type yang:counter64;
                                        units "bytes";
                                        description "Number of bytes discarded for a new session exhausting session store for a Protected Object.";
                                    }

                                    leaf packets {
                                        type yang:counter64;
                                        units "packets";
                                        description "Number of packets discarded for a new session exhausting session store for a Protected Object.";
                                    }

                                } // container session-exhaust


                                container mitigation-rules {
                                    description "Enter the mitigation-rules context";

                                    leaf octets {
                                        type yang:counter64;
                                        units "bytes";
                                        description
                                            "Number of bytes discarded by mitigation-rule entries for a Protected Object
                                             in the to-protected-object direction.";
                                    }

                                    leaf packets {
                                        type yang:counter64;
                                        units "packets";
                                        description
                                            "Number of packets discarded by mitigation-rule entries for a Protected Object
                                             in the to-protected-object direction.";
                                    }

                                    container client-authentication {
                                        description "Enter the client-authentication context";

                                        leaf octets {
                                            type yang:counter64;
                                            units "bytes";
                                            description "Number of bytes discarded by Client Authentication in mitigation-rule entries for the Protected Object.";
                                        }

                                        leaf packets {
                                            type yang:counter64;
                                            units "packets";
                                            description "Number of packets discarded by Client Authentication in mitigation-rule entries for the Protected Object.";
                                        }

                                    } // container client-authentication

                                } // container mitigation-rules


                            } // container discards

                            container generated {
                                description "Enter the generated context";

                                container tcp-reset {
                                    description "Enter the tcp-reset context";

                                    leaf octets {
                                        type yang:counter64;
                                        units "bytes";
                                        description "Number of bytes for TCP Resets generated towards a Protected Object.";
                                    }

                                    leaf packets {
                                        type yang:counter64;
                                        units "packets";
                                        description "Number of packets for TCP Resets generated towards a Protected Object.";
                                    }

                                } // container tcp-reset

                            } // container generated

                            container transmit {
                                description "Enter the transmit context";

                                leaf octets {
                                    type yang:counter64;
                                    units "bytes";
                                    description "Number of bytes transmitted for a Protected Object.";
                                }

                                leaf packets {
                                    type yang:counter64;
                                    units "packets";
                                    description "Number of packets transmitted for a Protected Object.";
                                }

                            } // container transmit

                        } // container to-protected-object

                        container from-protected-object {
                            description "Enter the from-protected-object context";

                            leaf tracked-sources-created {
                                type yang:counter64;
                                description
                                    "The all-time number of tracked source records created for this Protected
                                     Object for traffic in the outbound (from-protected-object) direction on
                                     the DMS esa-vm(s) since system startup.";
                            }

                            leaf flows-created {
                                type yang:counter64;
                                units "flows";
                                description
                                    "The all-time number of flow records created for this Protected
                                     Object for traffic in the outbound (from-protected-object direction on the DMS
                                     esa-vm(s) since system startup.";
                            }

                            container packet-qualifier-discards {
                                description "Enter the packet-qualifier-discards context";

                                container ipv4 {
                                    description "Enter the ipv4 context";

                                    container errors {
                                        description "Enter the errors context";

                                        leaf octets {
                                            type yang:counter64;
                                            units "bytes";
                                            description "Number of bytes discarded due to IPv4 errors for a Protected Object.";
                                        }

                                        leaf packets {
                                            type yang:counter64;
                                            units "packets";
                                            description "Number of packets discarded due to IPv4 errors for a Protected Object.";
                                        }

                                    } // container errors

                                    container tcp-errors {
                                        description "Enter the tcp-errors context";

                                        leaf octets {
                                            type yang:counter64;
                                            units "bytes";
                                            description "Number of bytes discarded due to IPv4 TCP packet errors for a Protected Object.";
                                        }

                                        leaf packets {
                                            type yang:counter64;
                                            units "packets";
                                            description "Number of packets discarded due to IPv4 TCP packet errors for a Protected Object.";
                                        }

                                    } // container tcp-errors

                                    container udp-errors {
                                        description "Enter the udp-errors context";

                                        leaf octets {
                                            type yang:counter64;
                                            units "bytes";
                                            description "Number of bytes discarded due to IPv4 UDP packet errors for a Protected Object.";
                                        }

                                        leaf packets {
                                            type yang:counter64;
                                            units "packets";
                                            description "Number of packets discarded due to IPv4 UDP packet errors for a Protected Object.";
                                        }

                                    } // container udp-errors

                                } // container ipv4

                                container ipv6 {
                                    description "Enter the ipv6 context";

                                    container errors {
                                        description "Enter the errors context";

                                        leaf octets {
                                            type yang:counter64;
                                            units "bytes";
                                            description "Number of bytes of discarded IPv6 packets with errors for a Protected Object.";
                                        }

                                        leaf packets {
                                            type yang:counter64;
                                            units "packets";
                                            description "Number of discarded IPv6 packets with errors for a Protected Object.";
                                        }

                                    } // container errors

                                    container tcp-errors {
                                        description "Enter the tcp-errors context";

                                        leaf octets {
                                            type yang:counter64;
                                            units "bytes";
                                            description "Number of bytes discarded due to IPv6 TCP packet errors for a Protected Object.";
                                        }

                                        leaf packets {
                                            type yang:counter64;
                                            units "packets";
                                            description "Number of packets discarded due to IPv6 TCP packet errors for a Protected Object.";
                                        }

                                    } // container tcp-errors

                                    container udp-errors {
                                        description "Enter the udp-errors context";

                                        leaf octets {
                                            type yang:counter64;
                                            units "bytes";
                                            description "Number of bytes discarded due to IPv6 UDP packet errors for a Protected Object.";
                                        }

                                        leaf packets {
                                            type yang:counter64;
                                            units "packets";
                                            description "Number of packets discarded due to IPv6 UDP packet errors for a Protected Object.";
                                        }

                                    } // container udp-errors

                                } // container ipv6

                            } // container packet-qualifier-discards

                            container receive {
                                description "Enter the receive context";

                                leaf octets {
                                    type yang:counter64;
                                    units "bytes";
                                    description
                                        "Number of bytes received for a Protected Object.  This does not include
                                         NIC discards";
                                }

                                leaf packets {
                                    type yang:counter64;
                                    units "packets";
                                    description
                                        "Number of packets received for a Protected Object.  This does not include
                                         NIC discards";
                                }

                            } // container receive

                            container bypass {
                                description "Enter the bypass context";

                                container pre-filter {
                                    description "Enter the pre-filter context";

                                    leaf octets {
                                        type yang:counter64;
                                        units "bytes";
                                        description "Number of bytes that bypassed outbound mitigation-rules by the pre-filter for a Protected Object.";
                                    }

                                    leaf packets {
                                        type yang:counter64;
                                        units "packets";
                                        description "Number of packets that bypassed outbound mitigation-rules by the pre-filter for a Protected Object.";
                                    }

                                } // container pre-filter

                                container ip-fragments {
                                    description "Enter the ip-fragments context";

                                    leaf octets {
                                        type yang:counter64;
                                        units "bytes";
                                        description "Number of bytes of IP subsequent fragments that bypassed outbound mitigation-rules for a Protected Object.";
                                    }

                                    leaf packets {
                                        type yang:counter64;
                                        units "packets";
                                        description "Number of packets of IP subsequent fragments that bypassed outbound mitigation-rules for a Protected Object.";
                                    }

                                } // container ip-fragments

                                container countermeasure {
                                    description "Enter the countermeasure context";

                                    leaf octets {
                                        type yang:counter64;
                                        units "bytes";
                                        description "Number of bytes of packets that bypassed outbound countermeasures for a Protected Object.";
                                    }

                                    leaf packets {
                                        type yang:counter64;
                                        units "packets";
                                        description "Number of packets that bypassed outbound countermeasures for a Protected Object.";
                                    }

                                } // container countermeasure

                            } // container bypass

                            container discards {
                                description "Enter the discards context";

                                container malformed {
                                    description "Enter the malformed context";

                                    leaf octets {
                                        type yang:counter64;
                                        units "bytes";
                                        description "Number of bytes discarded in malformed outbound packets for a Protected Object.";
                                    }

                                    leaf packets {
                                        type yang:counter64;
                                        units "packets";
                                        description "Number of malformed outbound packets discarded for a Protected Object.";
                                    }

                                } // container malformed

                                container checksum-verification {
                                    description "Enter the checksum-verification context";

                                    container ipv4 {
                                        description "Enter the ipv4 context";

                                        container tcp-errors {
                                            description "Enter the tcp-errors context";

                                            leaf octets {
                                                type yang:counter64;
                                                units "bytes";
                                                description "Number of bytes discarded due to IPv4 TCP checksum errors for a Protected Object.";
                                            }

                                            leaf packets {
                                                type yang:counter64;
                                                units "packets";
                                                description "Number of packets discarded due to IPv4 TCP checksum errors for a Protected Object.";
                                            }

                                        } // container tcp-errors

                                        container udp-errors {
                                            description "Enter the udp-errors context";

                                            leaf octets {
                                                type yang:counter64;
                                                units "bytes";
                                                description "Number of bytes discarded due to IPv4 UDP checksum errors for a Protected Object.";
                                            }

                                            leaf packets {
                                                type yang:counter64;
                                                units "packets";
                                                description "Number of packets discarded due to IPv4 UDP checksum errors for a Protected Object.";
                                            }

                                        } // container udp-errors

                                    } // container ipv4

                                    container ipv6 {
                                        description "Enter the ipv6 context";

                                        container tcp-errors {
                                            description "Enter the tcp-errors context";

                                            leaf octets {
                                                type yang:counter64;
                                                units "bytes";
                                                description "Number of bytes discarded due to IPv6 TCP checksum errors for a Protected Object.";
                                            }

                                            leaf packets {
                                                type yang:counter64;
                                                units "packets";
                                                description "Number of packets discarded due to IPv6 TCP checksum errors for a Protected Object.";
                                            }

                                        } // container tcp-errors

                                        container udp-errors {
                                            description "Enter the udp-errors context";

                                            leaf octets {
                                                type yang:counter64;
                                                units "bytes";
                                                description "Number of bytes discarded due to IPv6 UDP checksum errors for a Protected Object.";
                                            }

                                            leaf packets {
                                                type yang:counter64;
                                                units "packets";
                                                description "Number of packets discarded due to IPv6 UDP checksum errors for a Protected Object.";
                                            }

                                        } // container udp-errors

                                    } // container ipv6

                                } // container checksum-verification

                                container ip-fragments {
                                    description "Enter the ip-fragments context";

                                    leaf octets {
                                        type yang:counter64;
                                        units "bytes";
                                        description
                                            "Number of bytes of IP subsequent fragments that were discarded because the initial
                                             fragment was discarded for a Protected Object.";
                                    }

                                    leaf packets {
                                        type yang:counter64;
                                        units "packets";
                                        description
                                            "Number of packets of IP subsequent fragments that were discarded because the initial
                                             fragment was discarded for a Protected Object.";
                                    }

                                } // container ip-fragments

                                container pre-filter {
                                    description "Enter the pre-filter context";

                                    leaf octets {
                                        type yang:counter64;
                                        units "bytes";
                                        description "Number of bytes discarded by the outbound pre-filter for a Protected Object.";
                                    }

                                    leaf packets {
                                        type yang:counter64;
                                        units "packets";
                                        description "Number of packets discarded by the outbound pre-filter for a Protected Object.";
                                    }

                                } // container pre-filter

                                container source-limit {
                                    description "Enter the source-limit context";

                                    leaf octets {
                                        type yang:counter64;
                                        units "bytes";
                                        description "Number of bytes discarded for a new outbound source exceeding source limit for a Protected Object.";
                                    }

                                    leaf packets {
                                        type yang:counter64;
                                        units "packets";
                                        description "Number of packets discarded for a new outbound source exceeding source limit for a Protected Object.";
                                    }

                                } // container source-limit

                                container source-exhaust {
                                    description "Enter the source-exhaust context";

                                    leaf octets {
                                        type yang:counter64;
                                        units "bytes";
                                        description "Number of bytes discarded for a new outbound source exhausting source store for a Protected Object.";
                                    }

                                    leaf packets {
                                        type yang:counter64;
                                        units "packets";
                                        description "Number of packets discarded for a new outbound source exhausting source store for a Protected Object.";
                                    }

                                } // container source-exhaust




                                container mitigation-rules {
                                    description "Enter the mitigation-rules context";

                                    leaf octets {
                                        type yang:counter64;
                                        units "bytes";
                                        description
                                            "Number of bytes discarded by mitigation-rule entries for a Protected Object
                                             in the from-protected-object direction.";
                                    }

                                    leaf packets {
                                        type yang:counter64;
                                        units "packets";
                                        description
                                            "Number of packets discarded by mitigation-rule entries for a Protected Object
                                             in the from-protected-object direction.";
                                    }

                                } // container mitigation-rules


                            } // container discards

                            container generated {
                                description "Enter the generated context";

                                container mitigation-rules {
                                    description "Enter the mitigation-rules context";

                                    container client-authentication {
                                        description "Enter the client-authentication context";

                                        leaf octets {
                                            type yang:counter64;
                                            units "bytes";
                                            description "Number of bytes generated by Client Authentication actions of mitigation-rules for the Protected Object.";
                                        }

                                        leaf packets {
                                            type yang:counter64;
                                            units "packets";
                                            description "Number of packets generated by Client Authentication actions of mitigation-rules for the Protected Object.";
                                        }

                                    } // container client-authentication

                                } // container mitigation-rules

                            } // container generated

                            container transmit {
                                description "Enter the transmit context";

                                leaf octets {
                                    type yang:counter64;
                                    units "bytes";
                                    description "Number of bytes transmitted for a Protected Object.";
                                }

                                leaf packets {
                                    type yang:counter64;
                                    units "packets";
                                    description "Number of packets transmitted for a Protected Object.";
                                }

                            } // container transmit

                        } // container from-protected-object

                    } // container statistics

                    container status {
                        description "Enter the status context";

                        container resources {
                            description "Enter the resources context";

                            container tracked-sources {
                                description "Enter the tracked-sources context";

                                leaf current {
                                    type yang:gauge32;
                                    description
                                        "The current number of inbound tracked source records in-use for this
                                         Protected Object on the DMS esa-vm(s).";
                                }

                                leaf peak {
                                    type yang:gauge32;
                                    description
                                        "The peak number of inbound tracked source records in-use for this
                                         Protected Object on the DMS esa-vm(s) since system startup.";
                                }

                                leaf usage-status {
                                    type types-dms:resource-usage-status-type;
                                    description
                                        "The level of inbound source records in-use for this Protected Object
                                         on the DMS esa-vm(s) considering the configured tracked-source-limit.";
                                }

                            } // container tracked-sources

                            container sessions {
                                description "Enter the sessions context";

                                leaf current {
                                    type yang:gauge32;
                                    units "flows";
                                    description
                                        "The current number of session records initiated in the inbound direction
                                         in-use for this Protected Object on the DMS esa-vm(s).";
                                }

                                leaf peak {
                                    type yang:gauge32;
                                    units "flows";
                                    description
                                        "The peak number of session records initiated in the inbound direction
                                         in-use for this Protected Object on the DMS esa-vm(s) since system startup.";
                                }

                                leaf usage-status {
                                    type types-dms:resource-usage-status-type;
                                    description
                                        "The level of session records initiated in the inbound direction in-use for
                                         this Protected Object on the DMS esa-vm(s) considering the configured
                                         tracked-session-limit.";
                                }

                            } // container sessions

                            container flows {
                                description "Enter the flows context";

                                leaf current {
                                    type yang:gauge32;
                                    units "flows";
                                    description
                                        "The current number of inbound flow records in-use for this Protected
                                         Object on the DMS esa-vm(s).";
                                }

                                leaf peak {
                                    type yang:gauge32;
                                    units "flows";
                                    description
                                        "The peak number of inbound flow records in-use for this Protected
                                         Object on the DMS esa-vm(s) since system startup.";
                                }

                                leaf usage-status {
                                    type types-dms:resource-usage-status-type;
                                    description
                                        "The level of inbound flow records in-use for this Protected Object
                                         on the DMS esa-vm(s) considering the configured tracked-flow-limit.";
                                }

                            } // container flows

                            container outbound {
                                description "Enter the outbound context";

                                container tracked-sources {
                                    description "Enter the tracked-sources context";

                                    leaf current {
                                        type yang:gauge32;
                                        description
                                            "The current number of outbound tracked source records in-use for this
                                             Protected Object on the DMS esa-vm(s).";
                                    }

                                    leaf peak {
                                        type yang:gauge32;
                                        description
                                            "The peak number of outbound tracked source records in-use for this
                                             Protected Object on the DMS esa-vm(s) since system startup.";
                                    }

                                    leaf usage-status {
                                        type types-dms:resource-usage-status-type;
                                        description
                                            "The level of outbound source records in-use for this Protected Object on
                                             the DMS esa-vm(s) considering the configured outbound tracked-source-limit.";
                                    }

                                } // container tracked-sources


                            } // container outbound

                        } // container resources

                    } // container status

                } // container summary

                container policer {
                    description "Enter the policer context";

                    list source-event-count {
                        key "name";
                        description "Enter the source-event-count list instance";

                        leaf name {
                            type types-sros:named-item;
                            description "Uniquely identifies the policer template.";
                        }

                        container summary {
                            description "Enter the summary context";

                            container statistics {
                                description "Enter the statistics context";

                                leaf drop {
                                    type yang:counter64;
                                    description
                                        "Number of times the policer was exceeded and caused a drop.  For source granularity policers with
                                         dynamic-block enabled drops cause a transition of the source to the dynamic-block state.";
                                }

                            } // container statistics

                        } // container summary

                    } // list source-event-count

                    list source-event-rate {
                        key "name";
                        description "Enter the source-event-rate list instance";

                        leaf name {
                            type types-sros:named-item;
                            description "Uniquely identifies the policer template.";
                        }

                        container summary {
                            description "Enter the summary context";

                            container statistics {
                                description "Enter the statistics context";

                                leaf drop {
                                    type yang:counter64;
                                    description
                                        "Number of times the policer was exceeded and caused a drop.  For source granularity policers with
                                         dynamic-block enabled drops cause a transition of the source to the dynamic-block state.";
                                }

                            } // container statistics

                        } // container summary

                    } // list source-event-rate

                    list source-flow-count {
                        key "name";
                        description "Enter the source-flow-count list instance";

                        leaf name {
                            type types-sros:named-item;
                            description "Uniquely identifies the policer template.";
                        }

                        container summary {
                            description "Enter the summary context";

                            container statistics {
                                description "Enter the statistics context";

                                leaf drop {
                                    type yang:counter64;
                                    description
                                        "Number of times the policer was exceeded and caused a drop.  For source granularity policers with
                                         dynamic-block enabled drops cause a transition of the source to the dynamic-block state.";
                                }

                            } // container statistics

                        } // container summary

                    } // list source-flow-count

                    list source-flow-setup-rate {
                        key "name";
                        description "Enter the source-flow-setup-rate list instance";

                        leaf name {
                            type types-sros:named-item;
                            description "Uniquely identifies the policer template.";
                        }

                        container summary {
                            description "Enter the summary context";

                            container statistics {
                                description "Enter the statistics context";

                                leaf drop {
                                    type yang:counter64;
                                    description
                                        "Number of times the policer was exceeded and caused a drop.  For source granularity policers with
                                         dynamic-block enabled drops cause a transition of the source to the dynamic-block state.";
                                }

                            } // container statistics

                        } // container summary

                    } // list source-flow-setup-rate

                    list event-count {
                        key "name";
                        description "Enter the event-count list instance";

                        leaf name {
                            type types-sros:named-item;
                            description "Uniquely identifies the policer template.";
                        }

                        container summary {
                            description "Enter the summary context";

                            container statistics {
                                description "Enter the statistics context";

                                leaf drop {
                                    type yang:counter64;
                                    description
                                        "Number of times the policer was exceeded and caused a drop.  For source granularity policers with
                                         dynamic-block enabled drops cause a transition of the source to the dynamic-block state.";
                                }

                            } // container statistics

                        } // container summary

                    } // list event-count

                    list event-rate {
                        key "name";
                        description "Enter the event-rate list instance";

                        leaf name {
                            type types-sros:named-item;
                            description "Uniquely identifies the policer template.";
                        }

                        container summary {
                            description "Enter the summary context";

                            container statistics {
                                description "Enter the statistics context";

                                leaf drop {
                                    type yang:counter64;
                                    description
                                        "Number of times the policer was exceeded and caused a drop.  For source granularity policers with
                                         dynamic-block enabled drops cause a transition of the source to the dynamic-block state.";
                                }

                            } // container statistics

                        } // container summary

                    } // list event-rate

                    list flow-count {
                        key "name";
                        description "Enter the flow-count list instance";

                        leaf name {
                            type types-sros:named-item;
                            description "Uniquely identifies the policer template.";
                        }

                        container summary {
                            description "Enter the summary context";

                            container statistics {
                                description "Enter the statistics context";

                                leaf drop {
                                    type yang:counter64;
                                    description
                                        "Number of times the policer was exceeded and caused a drop.  For source granularity policers with
                                         dynamic-block enabled drops cause a transition of the source to the dynamic-block state.";
                                }

                            } // container statistics

                        } // container summary

                    } // list flow-count

                    list flow-setup-rate {
                        key "name";
                        description "Enter the flow-setup-rate list instance";

                        leaf name {
                            type types-sros:named-item;
                            description "Uniquely identifies the policer template.";
                        }

                        container summary {
                            description "Enter the summary context";

                            container statistics {
                                description "Enter the statistics context";

                                leaf drop {
                                    type yang:counter64;
                                    description
                                        "Number of times the policer was exceeded and caused a drop.  For source granularity policers with
                                         dynamic-block enabled drops cause a transition of the source to the dynamic-block state.";
                                }

                            } // container statistics

                        } // container summary

                    } // list flow-setup-rate

                } // container policer

                container protocol-handlers {
                    description "Enter the protocol-handlers context";

                    list dns-auto-protect {
                        key "name";
                        description "Enter the dns-auto-protect list instance";

                        leaf name {
                            type types-sros:named-item;
                            description "Specifies a name that uniquely identifies a dns-auto-protect object within a DMS Protected Object.";
                        }

                        list esa {
                            key "esa-id vm";
                            description "Enter the esa list instance";

                            leaf esa-id {
                                type leafref {
                                    path "../../../../../../esa/esa-id";
                                }
                                description "Specifies an ESA identifier.";
                            }

                            leaf vm {
                                type leafref {
                                    path "../../../../../../esa[esa-id=current()/../esa-id]/vm/vm-id";
                                }
                                description "Specifies the VM identifier within the ESA.";
                            }

                            container domain-name {
                                description "Enter the domain-name context";

                                container cache {
                                    description "Enter the cache context";

                                    leaf entries {
                                        type yang:gauge32;
                                        description "The total number of DNS domain-name entries in the cache.";
                                    }

                                    container insertion-rate {
                                        description "Enter the insertion-rate context";

                                        leaf current {
                                            type yang:gauge32;
                                            description "The current rate of domain-name insertions in the cache.";
                                        }

                                        leaf average {
                                            type yang:gauge32;
                                            description "The average rate of domain-name insertions in the cache within the last 60 minutes.";
                                        }

                                        leaf peak {
                                            type yang:gauge32;
                                            description "The peak rate of domain-name insertions in the cache.";
                                        }

                                    } // container insertion-rate

                                    container monitor {
                                        description "Enter the monitor context";

                                        container request-hit-ratio {
                                            description "Enter the request-hit-ratio context";

                                            leaf current {
                                                type uint32 {
                                                    range "0..10000";
                                                }
                                                units "centipercent";
                                                description
                                                    "The current ratio of dns requested domain-names that are in the cache against the total
                                                     amount of dns requests.  This only includes requests in the monitor state.";
                                            }

                                            leaf average {
                                                type uint32 {
                                                    range "0..10000";
                                                }
                                                units "centipercent";
                                                description
                                                    "The average ratio of dns requested domain-names that are in the cache against the total
                                                     amount of dns requests.  This only includes requests in the monitor state.";
                                            }

                                            leaf peak {
                                                type uint32 {
                                                    range "0..10000";
                                                }
                                                units "centipercent";
                                                description
                                                    "The peak ratio of dns requested domain-names that are in the cache against the total
                                                     amount of dns requests.  This only includes requests in the most recent monitor state.";
                                            }

                                        } // container request-hit-ratio

                                    } // container monitor

                                    container statistics {
                                        description "Enter the statistics context";

                                        leaf inserted {
                                            type yang:counter64;
                                            description "The total number of DNS domain-names inserted into the cache.";
                                        }

                                        leaf aged-out {
                                            type yang:counter64;
                                            description "The total number of DNS domain-names that aged out from the cache.";
                                        }

                                        leaf bumped {
                                            type yang:counter64;
                                            description
                                                "The total number of DNS domain-names that were still valid but were bumped by
                                                 a newer entry being added to the cache.";
                                        }

                                        leaf dropped {
                                            type yang:counter64;
                                            description "The total number of DNS domain-names that were unable to be added to the cache.";
                                        }

                                        leaf removed {
                                            type yang:counter64;
                                            description
                                                "The total number of DNS domain-names that were in the cache, but an error response
                                                 was recieved and the domain-name was removed.";
                                        }

                                    } // container statistics

                                } // container cache


                            } // container domain-name

                            container statistics {
                                description "Enter the statistics context";

                                container dns-responses {
                                    description "Enter the dns-responses context";

                                    leaf total {
                                        type yang:counter64;
                                        units "packets";
                                        description "The total number of DNS responses seen by the DNS auto-protect object.";
                                    }

                                    leaf success {
                                        type yang:counter64;
                                        units "packets";
                                        description "The number of DNS responses with a no-error(0) status code seen by the DNS auto-protect object.";
                                    }

                                    leaf error {
                                        type yang:counter64;
                                        units "packets";
                                        description "The number of DNS responses with an error status code seen by the DNS auto-protect object.";
                                    }

                                    leaf other {
                                        type yang:counter64;
                                        units "packets";
                                        description "The number of DNS responses with neither a success nor an error status code seen by the DNS auto-protect object.";
                                    }

                                    leaf invalid {
                                        type yang:counter64;
                                        units "packets";
                                        description "The number of DNS responses failing sanity checks seen by the DNS auto-protect object.";
                                    }

                                } // container dns-responses

                                container dns-requests {
                                    description "Enter the dns-requests context";

                                    container monitor {
                                        description "Enter the monitor context";

                                        leaf allowed {
                                            type yang:counter64;
                                            units "packets";
                                            description
                                                "The total number of DNS requests allowed by the DNS auto-protect object
                                                 in monitor mode.";
                                        }

                                        leaf dropped {
                                            type yang:counter64;
                                            units "packets";
                                            description
                                                "The total number of DNS requests that exceeded the DNS auto-protect limit
                                                 of simultaneous transactions per tracked session and were dropped.";
                                        }

                                    } // container monitor

                                    container protect {
                                        description "Enter the protect context";

                                        leaf allowed {
                                            type yang:counter64;
                                            units "packets";
                                            description
                                                "The total number of DNS requests allowed by the DNS auto-protect object
                                                 in protect mode.  These include un-filtered requests or requests that
                                                 matched success filter criteria.";
                                        }

                                        leaf leaked {
                                            type yang:counter64;
                                            units "packets";
                                            description
                                                "The total number of DNS requests that did not match the DNS auto-protect
                                                 success filter criteria in protect mode, but were leaked through to the PO.";
                                        }

                                        leaf dropped {
                                            type yang:counter64;
                                            units "packets";
                                            description
                                                "The total number of DNS requests that did not match the DNS auto-protect
                                                 success filter criteria or exceeded the DNS auto-protect limit of
                                                 simultaneous transactions per tracked session, and were dropped.";
                                        }

                                    } // container protect

                                } // container dns-requests

                            } // container statistics

                            container status {
                                description "Enter the status context";

                                leaf oper-state {
                                    type types-dms:dns-auto-protect-oper-state;
                                    description "Specifies the operational state of the dns-auto-protect object.";
                                }

                                leaf last-monitor-time {
                                    type yang:date-and-time;
                                    description "The most recent time of a transition of dns-auto-protect from the protect to the monitor state.";
                                }

                                leaf last-protect-time {
                                    type yang:date-and-time;
                                    description "The most recent time of a transition of dns-auto-protect from the monitor to the protect state.";
                                }

                                container monitor {
                                    description "Enter the monitor context";

                                    container error-rate {
                                        description "Enter the error-rate context";

                                        leaf current {
                                            type yang:gauge32;
                                            units "records per second";
                                            description
                                                "The current dns response error rate in monitor mode.  This includes DNS responses
                                                 with an error status code.";
                                        }

                                        leaf average {
                                            type yang:gauge32;
                                            units "records per second";
                                            description
                                                "The average dns response error rate in monitor mode.  This includes DNS responses
                                                 with an error status code.";
                                        }

                                        leaf peak {
                                            type yang:gauge32;
                                            units "records per second";
                                            description
                                                "The peak dns response error rate in the most recent monitor mode.  This includes
                                                 DNS responses with an error status code.";
                                        }

                                    } // container error-rate

                                } // container monitor

                                container protect {
                                    description "Enter the protect context";

                                    container error-rate {
                                        description "Enter the error-rate context";

                                        leaf current {
                                            type yang:gauge32;
                                            units "records per second";
                                            description
                                                "The current total error rate in protect mode.  This includes the sum of DNS
                                                 requests discarded by the domain-name-cache request filter and dns responses
                                                 with an error status code.";
                                        }

                                        leaf average {
                                            type yang:gauge32;
                                            units "records per second";
                                            description
                                                "The average total error rate in protect mode.  This includes the sum of DNS
                                                 requests discarded by the domain-name-cache request filter and dns responses
                                                 with an error status code.";
                                        }

                                        leaf peak {
                                            type yang:gauge32;
                                            units "records per second";
                                            description
                                                "The peak total error rate in the most recent protect mode.  This includes the sum of DNS
                                                 requests discarded by the domain-name-cache request filter and dns responses
                                                 with an error status code.";
                                        }

                                    } // container error-rate

                                } // container protect

                            } // container status

                        } // list esa

                        container summary {
                            description "Enter the summary context";

                            container domain-name {
                                description "Enter the domain-name context";

                                container cache {
                                    description "Enter the cache context";

                                    leaf entries {
                                        type yang:gauge32;
                                        description "The total number of DNS domain-name entries in the cache.";
                                    }

                                    container insertion-rate {
                                        description "Enter the insertion-rate context";

                                        leaf current {
                                            type yang:gauge32;
                                            description "The current rate of domain-name insertions in the cache.";
                                        }

                                        leaf average {
                                            type yang:gauge32;
                                            description "The average rate of domain-name insertions in the cache within the last 60 minutes.";
                                        }

                                        leaf peak {
                                            type yang:gauge32;
                                            description "The peak rate of domain-name insertions in the cache.";
                                        }

                                    } // container insertion-rate

                                    container monitor {
                                        description "Enter the monitor context";

                                        container request-hit-ratio {
                                            description "Enter the request-hit-ratio context";

                                            leaf current {
                                                type uint32 {
                                                    range "0..10000";
                                                }
                                                units "centipercent";
                                                description
                                                    "The current ratio of dns requested domain-names that are in the cache against the total
                                                     amount of dns requests.  This only includes requests in the monitor state.";
                                            }

                                            leaf average {
                                                type uint32 {
                                                    range "0..10000";
                                                }
                                                units "centipercent";
                                                description
                                                    "The average ratio of dns requested domain-names that are in the cache against the total
                                                     amount of dns requests.  This only includes requests in the monitor state.";
                                            }

                                            leaf peak {
                                                type uint32 {
                                                    range "0..10000";
                                                }
                                                units "centipercent";
                                                description
                                                    "The peak ratio of dns requested domain-names that are in the cache against the total
                                                     amount of dns requests.  This only includes requests in the most recent monitor state.";
                                            }

                                        } // container request-hit-ratio

                                    } // container monitor

                                    container statistics {
                                        description "Enter the statistics context";

                                        leaf inserted {
                                            type yang:counter64;
                                            description "The total number of DNS domain-names inserted into the cache.";
                                        }

                                        leaf aged-out {
                                            type yang:counter64;
                                            description "The total number of DNS domain-names that aged out from the cache.";
                                        }

                                        leaf bumped {
                                            type yang:counter64;
                                            description
                                                "The total number of DNS domain-names that were still valid but were bumped by
                                                 a newer entry being added to the cache.";
                                        }

                                        leaf dropped {
                                            type yang:counter64;
                                            description "The total number of DNS domain-names that were unable to be added to the cache.";
                                        }

                                        leaf removed {
                                            type yang:counter64;
                                            description
                                                "The total number of DNS domain-names that were in the cache, but an error response
                                                 was recieved and the domain-name was removed.";
                                        }

                                    } // container statistics

                                } // container cache


                            } // container domain-name

                            container statistics {
                                description "Enter the statistics context";

                                container dns-responses {
                                    description "Enter the dns-responses context";

                                    leaf total {
                                        type yang:counter64;
                                        units "packets";
                                        description "The total number of DNS responses seen by the DNS auto-protect object.";
                                    }

                                    leaf success {
                                        type yang:counter64;
                                        units "packets";
                                        description "The number of DNS responses with a no-error(0) status code seen by the DNS auto-protect object.";
                                    }

                                    leaf error {
                                        type yang:counter64;
                                        units "packets";
                                        description "The number of DNS responses with an error status code seen by the DNS auto-protect object.";
                                    }

                                    leaf other {
                                        type yang:counter64;
                                        units "packets";
                                        description "The number of DNS responses with neither a success nor an error status code seen by the DNS auto-protect object.";
                                    }

                                    leaf invalid {
                                        type yang:counter64;
                                        units "packets";
                                        description "The number of DNS responses failing sanity checks seen by the DNS auto-protect object.";
                                    }

                                } // container dns-responses

                                container dns-requests {
                                    description "Enter the dns-requests context";

                                    container monitor {
                                        description "Enter the monitor context";

                                        leaf allowed {
                                            type yang:counter64;
                                            units "packets";
                                            description
                                                "The total number of DNS requests allowed by the DNS auto-protect object
                                                 in monitor mode.";
                                        }

                                        leaf dropped {
                                            type yang:counter64;
                                            units "packets";
                                            description
                                                "The total number of DNS requests that exceeded the DNS auto-protect limit
                                                 of simultaneous transactions per tracked session and were dropped.";
                                        }

                                    } // container monitor

                                    container protect {
                                        description "Enter the protect context";

                                        leaf allowed {
                                            type yang:counter64;
                                            units "packets";
                                            description
                                                "The total number of DNS requests allowed by the DNS auto-protect object
                                                 in protect mode.  These include un-filtered requests or requests that
                                                 matched success filter criteria.";
                                        }

                                        leaf leaked {
                                            type yang:counter64;
                                            units "packets";
                                            description
                                                "The total number of DNS requests that did not match the DNS auto-protect
                                                 success filter criteria in protect mode, but were leaked through to the PO.";
                                        }

                                        leaf dropped {
                                            type yang:counter64;
                                            units "packets";
                                            description
                                                "The total number of DNS requests that did not match the DNS auto-protect
                                                 success filter criteria or exceeded the DNS auto-protect limit of
                                                 simultaneous transactions per tracked session, and were dropped.";
                                        }

                                    } // container protect

                                } // container dns-requests

                            } // container statistics

                            container status {
                                description "Enter the status context";

                                leaf oper-state {
                                    type types-dms:dns-auto-protect-oper-state;
                                    description "Specifies the operational state of the dns-auto-protect object.";
                                }

                                leaf last-monitor-time {
                                    type yang:date-and-time;
                                    description "The most recent time of a transition of dns-auto-protect from the protect to the monitor state.";
                                }

                                leaf last-protect-time {
                                    type yang:date-and-time;
                                    description "The most recent time of a transition of dns-auto-protect from the monitor to the protect state.";
                                }

                                container monitor {
                                    description "Enter the monitor context";

                                    container error-rate {
                                        description "Enter the error-rate context";

                                        leaf current {
                                            type yang:gauge32;
                                            units "records per second";
                                            description
                                                "The current dns response error rate in monitor mode.  This includes DNS responses
                                                 with an error status code.";
                                        }

                                        leaf average {
                                            type yang:gauge32;
                                            units "records per second";
                                            description
                                                "The average dns response error rate in monitor mode.  This includes DNS responses
                                                 with an error status code.";
                                        }

                                        leaf peak {
                                            type yang:gauge32;
                                            units "records per second";
                                            description
                                                "The peak dns response error rate in the most recent monitor mode.  This includes
                                                 DNS responses with an error status code.";
                                        }

                                    } // container error-rate

                                } // container monitor

                                container protect {
                                    description "Enter the protect context";

                                    container error-rate {
                                        description "Enter the error-rate context";

                                        leaf current {
                                            type yang:gauge32;
                                            units "records per second";
                                            description
                                                "The current total error rate in protect mode.  This includes the sum of DNS
                                                 requests discarded by the domain-name-cache request filter and dns responses
                                                 with an error status code.";
                                        }

                                        leaf average {
                                            type yang:gauge32;
                                            units "records per second";
                                            description
                                                "The average total error rate in protect mode.  This includes the sum of DNS
                                                 requests discarded by the domain-name-cache request filter and dns responses
                                                 with an error status code.";
                                        }

                                        leaf peak {
                                            type yang:gauge32;
                                            units "records per second";
                                            description
                                                "The peak total error rate in the most recent protect mode.  This includes the sum of DNS
                                                 requests discarded by the domain-name-cache request filter and dns responses
                                                 with an error status code.";
                                        }

                                    } // container error-rate

                                } // container protect

                            } // container status

                        } // container summary

                    } // list dns-auto-protect

                    list dns-validate {
                        key "name";
                        description "Enter the dns-validate list instance";

                        leaf name {
                            type types-sros:named-item;
                            description "Specifies a name that uniquely identifies a dns-validate object within a DMS Protected Object.";
                        }

                        container dns-filter {
                            description "Enter the dns-filter context";

                            list entry {
                                key "id";
                                description "Enter the entry list instance";

                                leaf id {
                                    type uint32 {
                                        range "1..16";
                                    }
                                    description
                                        "Uniquely identifies the DNS filter entry within the protected object DNS validator.
                                         Lower entry numbers take precedence";
                                }

                                container action {
                                    description "Enter the action context";

                                    container query-name-entropy-range {
                                        description "Enter the query-name-entropy-range context";

                                        container summary {
                                            description "Enter the summary context";

                                            list bin {
                                                key "bin-number";
                                                description "Enter the bin list instance";

                                                leaf bin-number {
                                                    type uint32 {
                                                        range "1..16";
                                                    }
                                                }

                                                container statistics {
                                                    description "Enter the statistics context";

                                                    leaf requests {
                                                        type yang:counter64;
                                                        description "Number of DNS requests where the query-name entropy was in the range for this bin.";
                                                    }

                                                } // container statistics

                                                container range {
                                                    description "Enter the range context";

                                                    leaf minimum {
                                                        type decimal64 {
                                                            fraction-digits 2;
                                                        }
                                                        description "The minimum DNS query-name entropy for this stats bin.";
                                                    }

                                                    leaf maximum {
                                                        type decimal64 {
                                                            fraction-digits 2;
                                                        }
                                                        description "The maximum DNS query-name entropy for this stats bin.";
                                                    }

                                                } // container range

                                            } // list bin

                                        } // container summary

                                    } // container query-name-entropy-range

                                } // container action

                                container summary {
                                    description "Enter the summary context";

                                    container statistics {
                                        description "Enter the statistics context";

                                        container admit {
                                            description "Enter the admit context";

                                            leaf octets {
                                                type yang:counter64;
                                                units "bytes";
                                                description "Number of bytes admitted by actions of this dns-filter entry.";
                                            }

                                            leaf packets {
                                                type yang:counter64;
                                                units "packets";
                                                description "Number of packets admitted by actions of this dns-filter entry.";
                                            }

                                        } // container admit

                                        container discard {
                                            description "Enter the discard context";

                                            leaf octets {
                                                type yang:counter64;
                                                units "bytes";
                                                description "Total number of bytes discarded by all actions of this dns-filter entry.";
                                            }

                                            leaf packets {
                                                type yang:counter64;
                                                units "packets";
                                                description "Total number of packets discarded by all actions of this dns-filter entry.";
                                            }

                                            container action {
                                                description "Enter the action context";

                                                container drop {
                                                    description "Enter the drop context";

                                                    leaf octets {
                                                        type yang:counter64;
                                                        units "bytes";
                                                        description "Number of bytes discarded by the drop action of this dns-filter entry.";
                                                    }

                                                    leaf packets {
                                                        type yang:counter64;
                                                        units "packets";
                                                        description "Number of packets discarded by the drop action of this dns-filter entry.";
                                                    }

                                                } // container drop

                                                container dns-auto-protect {
                                                    description "Enter the dns-auto-protect context";

                                                    leaf octets {
                                                        type yang:counter64;
                                                        units "bytes";
                                                        description "Number of bytes discarded by the dns-auto-protect action of this dns-filter entry.";
                                                    }

                                                    leaf packets {
                                                        type yang:counter64;
                                                        units "packets";
                                                        description "Number of packets discarded by the dns-auto-protect action of this dns-filter entry.";
                                                    }

                                                } // container dns-auto-protect

                                                container protected-object-request-rate {
                                                    description "Enter the protected-object-request-rate context";

                                                    leaf octets {
                                                        type yang:counter64;
                                                        units "bytes";
                                                        description "Number of bytes discarded by the PO request rate policer action of this dns-filter entry.";
                                                    }

                                                    leaf packets {
                                                        type yang:counter64;
                                                        units "packets";
                                                        description "Number of packets discarded by the PO request rate policer action of this dns-filter entry.";
                                                    }

                                                } // container protected-object-request-rate

                                                container source-request-rate {
                                                    description "Enter the source-request-rate context";

                                                    leaf octets {
                                                        type yang:counter64;
                                                        units "bytes";
                                                        description "Number of bytes discarded by the source request rate policer action of this dns-filter entry.";
                                                    }

                                                    leaf packets {
                                                        type yang:counter64;
                                                        units "packets";
                                                        description "Number of packets discarded by the source request rate policer action of this dns-filter entry.";
                                                    }

                                                } // container source-request-rate

                                                container query-name-entropy-out-of-range {
                                                    description "Enter the query-name-entropy-out-of-range context";

                                                    leaf octets {
                                                        type yang:counter64;
                                                        units "bytes";
                                                        description "Number of bytes discarded by the query-name entropy range action of this dns-filter entry.";
                                                    }

                                                    leaf packets {
                                                        type yang:counter64;
                                                        units "packets";
                                                        description "Number of packets discarded by the query-name entropy range action of this dns-filter entry.";
                                                    }

                                                } // container query-name-entropy-out-of-range

                                            } // container action

                                        } // container discard

                                    } // container statistics

                                } // container summary

                            } // list entry

                            list esa {
                                key "esa-id vm";
                                description "Enter the esa list instance";

                                leaf esa-id {
                                    type leafref {
                                        path "../../../../../../../esa/esa-id";
                                    }
                                    description "Specifies an ESA identifier.";
                                }

                                leaf vm {
                                    type leafref {
                                        path "../../../../../../../esa[esa-id=current()/../esa-id]/vm/vm-id";
                                    }
                                    description "Specifies the VM identifier within the ESA.";
                                }

                                leaf oper-state {
                                    type types-sros:oper-state;
                                    description "Specifies the operational state of the dns-filter.";
                                }

                                leaf oper-flags {
                                    type types-dms:dns-filter-oper-flags-type;
                                    description "The different conditions that affect the operating status of dms-filter.";
                                }

                                container statistics {
                                    description "Enter the statistics context";

                                    leaf default-action {
                                        type yang:counter64;
                                        description
                                            "Number of times that none of the filter entries matched and the
                                             default-action was taken for this dns-filter.";
                                    }

                                    container default-action-drop {
                                        description "Enter the default-action-drop context";

                                        leaf octets {
                                            type yang:counter64;
                                            units "bytes";
                                            description "Number of bytes discarded by the default drop action of this dns-filter.";
                                        }

                                        leaf packets {
                                            type yang:counter64;
                                            units "packets";
                                            description "Number of packets discarded by the default drop action of this dns-filter.";
                                        }

                                    } // container default-action-drop

                                } // container statistics

                            } // list esa

                            container summary {
                                description "Enter the summary context";

                                leaf oper-state {
                                    type types-sros:oper-state;
                                    description "Specifies the operational state of the dns-filter.";
                                }

                                leaf oper-flags {
                                    type types-dms:dns-filter-oper-flags-type;
                                    description "The different conditions that affect the operating status of dms-filter.";
                                }

                                container statistics {
                                    description "Enter the statistics context";

                                    leaf default-action {
                                        type yang:counter64;
                                        description
                                            "Number of times that none of the filter entries matched and the
                                             default-action was taken for this dns-filter.";
                                    }

                                    container default-action-drop {
                                        description "Enter the default-action-drop context";

                                        leaf octets {
                                            type yang:counter64;
                                            units "bytes";
                                            description "Number of bytes discarded by the default drop action of this dns-filter.";
                                        }

                                        leaf packets {
                                            type yang:counter64;
                                            units "packets";
                                            description "Number of packets discarded by the default drop action of this dns-filter.";
                                        }

                                    } // container default-action-drop

                                } // container statistics

                            } // container summary

                        } // container dns-filter

                        container query-name-entropy-range {
                            description "Enter the query-name-entropy-range context";

                            container summary {
                                description "Enter the summary context";

                                list bin {
                                    key "bin-number";
                                    description "Enter the bin list instance";

                                    leaf bin-number {
                                        type uint32 {
                                            range "1..16";
                                        }
                                    }

                                    container statistics {
                                        description "Enter the statistics context";

                                        leaf requests {
                                            type yang:counter64;
                                            description "Number of DNS requests where the query-name entropy was in the range for this bin.";
                                        }

                                    } // container statistics

                                    container range {
                                        description "Enter the range context";

                                        leaf minimum {
                                            type decimal64 {
                                                fraction-digits 2;
                                            }
                                            description "The minimum DNS query-name entropy for this stats bin.";
                                        }

                                        leaf maximum {
                                            type decimal64 {
                                                fraction-digits 2;
                                            }
                                            description "The maximum DNS query-name entropy for this stats bin.";
                                        }

                                    } // container range

                                } // list bin

                            } // container summary

                        } // container query-name-entropy-range

                        container summary {
                            description "Enter the summary context";

                            container statistics {
                                description "Enter the statistics context";

                                container admit {
                                    description "Enter the admit context";

                                    leaf octets {
                                        type yang:counter64;
                                        units "bytes";
                                        description "Number of bytes admitted by dns-validate.";
                                    }

                                    leaf packets {
                                        type yang:counter64;
                                        units "packets";
                                        description "Number of packets admitted by dns-validate.";
                                    }

                                } // container admit

                                container bypass {
                                    description "Enter the bypass context";

                                    container ip-fragment {
                                        description "Enter the ip-fragment context";

                                        leaf octets {
                                            type yang:counter64;
                                            units "bytes";
                                            description "Number of IP fragment bytes bypassed by dns-validate.";
                                        }

                                        leaf packets {
                                            type yang:counter64;
                                            units "packets";
                                            description "Number of IP fragment packets bypassed by dns-validate.";
                                        }

                                    } // container ip-fragment

                                } // container bypass

                                container discard {
                                    description "Enter the discard context";

                                    container query-name-entropy-out-of-range {
                                        description "Enter the query-name-entropy-out-of-range context";

                                        leaf octets {
                                            type yang:counter64;
                                            units "bytes";
                                            description
                                                "Number of bytes discarded by the dns-validate due to the query-name
                                                 entropy being out of the configured range.";
                                        }

                                        leaf packets {
                                            type yang:counter64;
                                            units "packets";
                                            description
                                                "Number of packets discarded by the dns-validate due to the query-name
                                                 entropy being out of the configured range.";
                                        }

                                    } // container query-name-entropy-out-of-range

                                    container invalid-ip-protocol {
                                        description "Enter the invalid-ip-protocol context";

                                        leaf octets {
                                            type yang:counter64;
                                            units "bytes";
                                            description
                                                "Number of bytes discarded by the dns-validate due to the ip-protocol of
                                                 the DNS message not being UDP.";
                                        }

                                        leaf packets {
                                            type yang:counter64;
                                            units "packets";
                                            description
                                                "Number of packets discarded by the dns-validate due to the ip-protocol of
                                                 the DNS message not being UDP.";
                                        }

                                    } // container invalid-ip-protocol

                                    container message-size {
                                        description "Enter the message-size context";

                                        leaf octets {
                                            type yang:counter64;
                                            units "bytes";
                                            description
                                                "Number of bytes discarded by the dns-validate due to the DNS message
                                                 size being larger than the configured limit.";
                                        }

                                        leaf packets {
                                            type yang:counter64;
                                            units "packets";
                                            description
                                                "Number of packets discarded by the dns-validate due to the DNS message
                                                 size being larger than the configured limit.";
                                        }

                                    } // container message-size

                                    container packet-sanity {
                                        description "Enter the packet-sanity context";

                                        leaf octets {
                                            type yang:counter64;
                                            units "bytes";
                                            description
                                                "Number of bytes discarded by the dns-validate due to the DNS
                                                 packet failing sanity checks.";
                                        }

                                        leaf packets {
                                            type yang:counter64;
                                            units "packets";
                                            description
                                                "Number of packets discarded by the dns-validate due to the DNS
                                                 packet failing sanity checks.";
                                        }

                                    } // container packet-sanity

                                    container other {
                                        description "Enter the other context";

                                        leaf octets {
                                            type yang:counter64;
                                            units "bytes";
                                            description
                                                "Number of bytes discarded by the dns-validate for other reasons that
                                                 are not malicious and therefore are not subject to dynamic-block.
                                                 (eg TCP segmented DNS request).";
                                        }

                                        leaf packets {
                                            type yang:counter64;
                                            units "packets";
                                            description
                                                "Number of packets discarded by the dns-validate for other reasons that
                                                 are not malicious and therefore are not subject to dynamic-block.
                                                 (eg TCP segmented DNS request).";
                                        }

                                    } // container other

                                    container protected-object-request-rate {
                                        description "Enter the protected-object-request-rate context";

                                        leaf octets {
                                            type yang:counter64;
                                            units "bytes";
                                            description
                                                "Number of bytes discarded by the dns-validate due to the DNS request
                                                 rate at the Protected Object scope exceeding the configured limit
                                                 in the event-rate policer.";
                                        }

                                        leaf packets {
                                            type yang:counter64;
                                            units "packets";
                                            description
                                                "Number of packets discarded by the dns-validate due to the DNS request
                                                 rate at the Protected Object scope exceeding the configured limit
                                                 in the event-rate policer.";
                                        }

                                    } // container protected-object-request-rate

                                    container source-request-rate {
                                        description "Enter the source-request-rate context";

                                        leaf octets {
                                            type yang:counter64;
                                            units "bytes";
                                            description
                                                "Number of bytes discarded by the dns-validate due to the DNS request
                                                 rate at the Source scope exceeding the configured limit in the
                                                 event-rate policer.";
                                        }

                                        leaf packets {
                                            type yang:counter64;
                                            units "packets";
                                            description
                                                "Number of packets discarded by the dns-validate due to the DNS request
                                                 rate at the Source scope exceeding the configured limit in the
                                                 event-rate policer.";
                                        }

                                    } // container source-request-rate

                                } // container discard

                                container events {
                                    description "Enter the events context";

                                    leaf dynamic-block {
                                        type yang:counter64;
                                        description "Number of times dns-validate caused a source to transition to the dynamic-block state.";
                                    }

                                } // container events

                            } // container statistics

                        } // container summary

                    } // list dns-validate

                    list dns-tracker {
                        key "dns-tracker-name";
                        description "Enter the dns-tracker list instance";

                        leaf dns-tracker-name {
                            type types-sros:named-item;
                            description "Specifies a name that uniquely identifies a dns-tracker within a DMS Protected Object.";
                        }

                        container summary {
                            description "Enter the summary context";

                            container statistics {
                                description "Enter the statistics context";

                                container events {
                                    description "Enter the events context";

                                    leaf dynamic-block {
                                        type yang:counter64;
                                        description "Number of times dns-tracker caused a source to transition to the dynamic-block state.";
                                    }

                                } // container events

                                container flows {
                                    description "Enter the flows context";

                                    leaf created {
                                        type yang:counter64;
                                        units "flows";
                                        description "Number of times that a TCP flow was created for this dns-tracker.";
                                    }

                                    leaf created-mate {
                                        type yang:counter64;
                                        units "flows";
                                        description "Number of times that a mate TCP flow was created for this dns-tracker.";
                                    }

                                    container abandoned-protocol-tracking {
                                        description "Enter the abandoned-protocol-tracking context";

                                        leaf ip-fragment {
                                            type yang:counter64;
                                            units "flows";
                                            description
                                                "Number of times that protocol tracking of a DNS over TCP session was abandoned
                                                 due to receipt of an IP fragment during payload protocol inspection.";
                                        }

                                    } // container abandoned-protocol-tracking

                                    container blocked {
                                        description "Enter the blocked context";

                                        leaf tcp-midstream {
                                            type yang:counter64;
                                            units "flows";
                                            description
                                                "Number of times that the dns-tracker blocked flow creation due to
                                                 the initial TCP packet of the flow not having the Syn flag set.";
                                        }

                                        leaf tcp-syn-ack {
                                            type yang:counter64;
                                            units "flows";
                                            description
                                                "Number of times that the dns-tracker blocked flow creation due to
                                                 a TCP SYN-ACK received in the mitigation rule direction.";
                                        }

                                        leaf invalid-ip-protocol {
                                            type yang:counter64;
                                            units "flows";
                                            description
                                                "Number of times that the dns-tracker blocked flow creation due to
                                                 the initial IP packet of the flow not being the expected protocol.";
                                        }

                                    } // container blocked

                                    container closed {
                                        description "Enter the closed context";

                                        leaf incomplete-tcp-handshake {
                                            type yang:counter64;
                                            units "flows";
                                            description
                                                "Number of times that the dns-tracker closed flows due to an excessive time gap
                                                 between the initial TCP handshake Syn and subsequent Ack.";
                                        }

                                        leaf start-guard-time {
                                            type yang:counter64;
                                            units "flows";
                                            description
                                                "Number of times that the dns-tracker closed flows due to the time between the
                                                 TCP handshake and the DNS request exceeding the configured start guard time.";
                                        }

                                        leaf invalid-dns {
                                            type yang:counter64;
                                            units "flows";
                                            description
                                                "Number of times that the dns-tracker closed DNS client flows because they did
                                                 not start with a SYN.";
                                        }

                                        leaf payload-validate {
                                            type yang:counter64;
                                            units "flows";
                                            description
                                                "Number of times that the dns-tracker closed flows due to the TCP payload
                                                 being discarded by the DNS validator configured as payload-validate.";
                                        }

                                        leaf tcp-segment-out-of-sequence {
                                            type yang:counter64;
                                            units "flows";
                                            description
                                                "Number of times that the dns-tracker closed flows due to the TCP payload
                                                 being out of sequence.";
                                        }

                                        leaf tcp-protocol-violation {
                                            type yang:counter64;
                                            units "flows";
                                            description "Number of times that the dns-tracker closed flows due to a TCP protocol violation.";
                                        }

                                        leaf inactivity {
                                            type yang:counter64;
                                            units "flows";
                                            description
                                                "Number of times that the dns-tracker closed flows due to the time between
                                                 packets exceeding the configured DNS tracker (or TCP) inactivity timeout.";
                                        }

                                        leaf interrupted {
                                            type yang:counter64;
                                            units "flows";
                                            description "Number of times that the dns-tracker closed flows after having seen a TCP RST.";
                                        }

                                        leaf completed {
                                            type yang:counter64;
                                            units "flows";
                                            description "Number of times that the dns-tracker closed flows after having seen a TCP FIN.";
                                        }

                                    } // container closed

                                    container udp {
                                        description "Enter the udp context";

                                        leaf created {
                                            type yang:counter64;
                                            units "flows";
                                            description "Number of times that a UDP flow was created for this dns-tracker.";
                                        }

                                        leaf created-mate {
                                            type yang:counter64;
                                            units "flows";
                                            description "Number of times that a UDP mate flow was created for this dns-tracker.";
                                        }

                                        container abandoned-protocol-tracking {
                                            description "Enter the abandoned-protocol-tracking context";

                                            leaf ip-fragment {
                                                type yang:counter64;
                                                units "flows";
                                                description
                                                    "Number of times that protocol tracking of a DNS over UDP  session was abandoned
                                                     due to receipt of an IP fragment during payload protocol inspection.";
                                            }

                                        } // container abandoned-protocol-tracking

                                        container blocked {
                                            description "Enter the blocked context";

                                            leaf payload-validate {
                                                type yang:counter64;
                                                units "flows";
                                                description
                                                    "Number of times that the dns-tracker blocked flow creation due to the UDP payload
                                                     being discarded by the DNS validator configured as payload-validate.";
                                            }

                                        } // container blocked

                                        container closed {
                                            description "Enter the closed context";

                                            leaf inactivity {
                                                type yang:counter64;
                                                units "flows";
                                                description
                                                    "Number of times that the dns-tracker closed UDP flows due to the time between
                                                     packets exceeding the configured DNS tracker (or UDP) inactivity timeout.";
                                            }

                                            leaf payload-validate {
                                                type yang:counter64;
                                                units "flows";
                                                description
                                                    "Number of times that the dns-tracker closed UDP flows due to the UDP payload
                                                     being discarded by the DNS validator configured as payload-validate.";
                                            }

                                        } // container closed

                                    } // container udp

                                } // container flows

                            } // container statistics

                        } // container summary

                    } // list dns-tracker


                    list http-tracker {
                        key "http-tracker-name";
                        description "Enter the http-tracker list instance";

                        leaf http-tracker-name {
                            type types-sros:named-item;
                            description "Specifies a name that uniquely identifies an http-tracker within a DMS Protected Object.";
                        }

                        container summary {
                            description "Enter the summary context";

                            container statistics {
                                description "Enter the statistics context";

                                container events {
                                    description "Enter the events context";

                                    leaf dynamic-block {
                                        type yang:counter64;
                                        description "Number of times http-tracker caused a source to transition to the dynamic-block state.";
                                    }

                                    leaf tolerance {
                                        type yang:counter64;
                                        description
                                            "Number of times that an HTTP request contained a non-standard request method.
                                             This would have caused the http flow to be discarded, but was allowed under
                                             lenient tolerance.";
                                    }

                                } // container events

                                container flows {
                                    description "Enter the flows context";

                                    leaf created {
                                        type yang:counter64;
                                        units "flows";
                                        description "Number of times that a flow was created for this http-tracker.";
                                    }

                                    leaf created-mate {
                                        type yang:counter64;
                                        units "flows";
                                        description "Number of times that a mate flow was created for this http-tracker.";
                                    }

                                    container abandoned-protocol-tracking {
                                        description "Enter the abandoned-protocol-tracking context";

                                        leaf ip-fragment {
                                            type yang:counter64;
                                            units "flows";
                                            description
                                                "Number of times that protocol tracking of an HTTP session was abandoned due
                                                 to receipt of an IP fragment during payload protocol inspection.";
                                        }

                                        leaf tolerance {
                                            type yang:counter64;
                                            units "flows";
                                            description
                                                "Number of times that protocol tracking of an HTTP session was abandoned due
                                                 to receipt of a packet during payload protocol inspection that would have
                                                 been discarded, but was allowed under lenient tolerance.";
                                        }

                                    } // container abandoned-protocol-tracking

                                    container blocked {
                                        description "Enter the blocked context";

                                        leaf tcp-midstream {
                                            type yang:counter64;
                                            units "flows";
                                            description
                                                "Number of times that the http-tracker blocked flow creation due to
                                                 the initial TCP packet of the flow not having the Syn flag set.";
                                        }

                                        leaf tcp-syn-ack {
                                            type yang:counter64;
                                            units "flows";
                                            description
                                                "Number of times that the http-tracker blocked flow creation due to
                                                 a TCP SYN-ACK received in the mitigation rule direction.";
                                        }

                                        leaf invalid-ip-protocol {
                                            type yang:counter64;
                                            units "flows";
                                            description
                                                "Number of times that the http-tracker blocked flow creation due to
                                                 the initial IP packet of the flow not being the expected protocol.";
                                        }

                                    } // container blocked

                                    container closed {
                                        description "Enter the closed context";

                                        leaf incomplete-tcp-handshake {
                                            type yang:counter64;
                                            units "flows";
                                            description
                                                "Number of times that the http-tracker closed flows due to an excessive time gap
                                                 between the initial TCP handshake Syn and subsequent Ack.";
                                        }

                                        leaf start-guard-time {
                                            type yang:counter64;
                                            units "flows";
                                            description
                                                "Number of times that the http-tracker closed flows due to the time between the
                                                 TCP handshake and the HTTP request exceeding the configured start guard time.";
                                        }

                                        leaf invalid-http {
                                            type yang:counter64;
                                            units "flows";
                                            description
                                                "Number of times that the http-tracker closed flows due to the packet content
                                                 not being HTTP.";
                                        }

                                        leaf authentication-ineligible {
                                            type yang:counter64;
                                            units "flows";
                                            description
                                                "Number of times that the http-tracker closed flows that needed http client
                                                 authentication, but the content of the flow was ineligible for authentication.";
                                        }

                                        leaf request-out-of-sequence {
                                            type yang:counter64;
                                            units "flows";
                                            description
                                                "Number of times that the http-tracker closed flows due to the http request
                                                 TCP segments being out of sequence.";
                                        }

                                        leaf request-guard-time {
                                            type yang:counter64;
                                            units "flows";
                                            description
                                                "Number of times that the http-tracker closed flows due to the time between the
                                                 beginning and end of an HTTP request header exceeding the configured request
                                                 guard time.";
                                        }

                                        leaf request-rate {
                                            type yang:counter64;
                                            units "flows";
                                            description
                                                "Number of times that the http-tracker closed flows due to the http request rate
                                                 exceeding the configured protected-object granularity request rate policers.";
                                        }

                                        leaf source-request-rate {
                                            type yang:counter64;
                                            units "flows";
                                            description
                                                "Number of times that the http-tracker closed flows due to the http request rate
                                                 exceeding the configured source granularity request rate policers.";
                                        }

                                        leaf tcp-protocol-violation {
                                            type yang:counter64;
                                            units "flows";
                                            description "Number of times that the http-tracker closed flows due to a TCP protocol violation.";
                                        }

                                        leaf inactivity {
                                            type yang:counter64;
                                            units "flows";
                                            description
                                                "Number of times that the http-tracker closed flows due to the time between
                                                 packets exceeding the configured HTTP tracker (or TCP) inactivity timeout.";
                                        }

                                        leaf interrupted {
                                            type yang:counter64;
                                            units "flows";
                                            description "Number of times that the http-tracker closed flows after having seen a TCP RST.";
                                        }

                                        leaf completed {
                                            type yang:counter64;
                                            units "flows";
                                            description "Number of times that the http-tracker closed flows after having seen a TCP FIN.";
                                        }

                                    } // container closed

                                } // container flows

                            } // container statistics

                        } // container summary

                    } // list http-tracker

                    list icmp-validate {
                        key "name";
                        description "Enter the icmp-validate list instance";

                        leaf name {
                            type types-sros:named-item;
                            description
                                "Specifies a name that uniquely identifies an icmp-validate object within
                                 a DMS Protected Object.";
                        }

                        container summary {
                            description "Enter the summary context";

                            container statistics {
                                description "Enter the statistics context";

                                container admit {
                                    description "Enter the admit context";

                                    leaf octets {
                                        type yang:counter64;
                                        units "bytes";
                                        description "Number of bytes admitted by icmp-validate.";
                                    }

                                    leaf packets {
                                        type yang:counter64;
                                        units "packets";
                                        description "Number of packets admitted by icmp-validate.";
                                    }

                                } // container admit

                                container bypass {
                                    description "Enter the bypass context";

                                    container ip-fragment {
                                        description "Enter the ip-fragment context";

                                        leaf octets {
                                            type yang:counter64;
                                            units "bytes";
                                            description "Number of IP fragment bytes bypassed by icmp-validate.";
                                        }

                                        leaf packets {
                                            type yang:counter64;
                                            units "packets";
                                            description "Number of IP fragment packets bypassed by icmp-validate.";
                                        }

                                    } // container ip-fragment

                                } // container bypass

                                container discard {
                                    description "Enter the discard context";

                                    container invalid-ip-protocol {
                                        description "Enter the invalid-ip-protocol context";

                                        leaf octets {
                                            type yang:counter64;
                                            units "bytes";
                                            description
                                                "Number of bytes discarded by the icmp-validate due to the ip-protocol of
                                                 the ICMP packet not being ICMP or ICMPv6.";
                                        }

                                        leaf packets {
                                            type yang:counter64;
                                            units "packets";
                                            description
                                                "Number of packets discarded by the icmp-validate due to the ip-protocol of
                                                 the ICMP packet not being ICMP or ICMPv6.";
                                        }

                                    } // container invalid-ip-protocol

                                    container packet-sanity {
                                        description "Enter the packet-sanity context";

                                        leaf octets {
                                            type yang:counter64;
                                            units "bytes";
                                            description
                                                "Number of bytes discarded by icmp-validate due to the ICMP
                                                 packet failing sanity checks.";
                                        }

                                        leaf packets {
                                            type yang:counter64;
                                            units "packets";
                                            description
                                                "Number of packets discarded by icmp-validate due to the ICMP
                                                 packet failing sanity checks.";
                                        }

                                    } // container packet-sanity

                                    container protected-object-packet-rate {
                                        description "Enter the protected-object-packet-rate context";

                                        leaf octets {
                                            type yang:counter64;
                                            units "bytes";
                                            description
                                                "Number of bytes discarded by icmp-validate due to the ICMP packet
                                                 rate at the Protected Object scope exceeding the configured limit
                                                 in the event-rate policer.";
                                        }

                                        leaf packets {
                                            type yang:counter64;
                                            units "packets";
                                            description
                                                "Number of packets discarded by icmp-validate due to the ICMP packet
                                                 rate at the Protected Object scope exceeding the configured limit
                                                 in the event-rate policer.";
                                        }

                                    } // container protected-object-packet-rate

                                    container source-packet-rate {
                                        description "Enter the source-packet-rate context";

                                        leaf octets {
                                            type yang:counter64;
                                            units "bytes";
                                            description
                                                "Number of bytes discarded by icmp-validate due to the ICMP packet
                                                 rate at the Source scope exceeding the configured limit in the
                                                 event-rate policer.";
                                        }

                                        leaf packets {
                                            type yang:counter64;
                                            units "packets";
                                            description
                                                "Number of packets discarded by icmp-validate due to the ICMP packet
                                                 rate at the Source scope exceeding the configured limit in the
                                                 event-rate policer.";
                                        }

                                    } // container source-packet-rate

                                } // container discard

                                container events {
                                    description "Enter the events context";

                                    leaf dynamic-block {
                                        type yang:counter64;
                                        description "Number of times icmp-validate caused a source to transition to the dynamic-block state.";
                                    }

                                } // container events

                            } // container statistics

                        } // container summary

                    } // list icmp-validate

                    list quic-tracker {
                        key "quic-tracker-name";
                        description "Enter the quic-tracker list instance";

                        leaf quic-tracker-name {
                            type types-sros:named-item;
                            description "Specifies a name that uniquely identifies a quic-tracker within a DMS Protected Object.";
                        }

                        container summary {
                            description "Enter the summary context";

                            container statistics {
                                description "Enter the statistics context";

                                container events {
                                    description "Enter the events context";

                                    leaf dynamic-block {
                                        type yang:counter64;
                                        description "Number of times quic-tracker caused a source to transition to the dynamic-block state.";
                                    }

                                } // container events

                                container flows {
                                    description "Enter the flows context";

                                    leaf created {
                                        type yang:counter64;
                                        units "flows";
                                        description "Number of times that a flow was created for this quic-tracker.";
                                    }

                                    leaf created-mate {
                                        type yang:counter64;
                                        units "flows";
                                        description "Number of times that a mate flow was created for this quic-tracker.";
                                    }

                                    container abandoned-protocol-tracking {
                                        description "Enter the abandoned-protocol-tracking context";

                                        leaf ip-fragment {
                                            type yang:counter64;
                                            units "flows";
                                            description
                                                "Number of times that protocol tracking of a QUIC session was abandoned due
                                                 to receipt of an IP fragment during payload protocol inspection.";
                                        }

                                    } // container abandoned-protocol-tracking

                                    container blocked {
                                        description "Enter the blocked context";

                                        leaf midstream {
                                            type yang:counter64;
                                            units "flows";
                                            description
                                                "Number of times that the quic-tracker blocked flow creation due to
                                                 a midstream QUIC packet that cannot be authenticated.";
                                        }

                                        leaf invalid-ip-protocol {
                                            type yang:counter64;
                                            units "flows";
                                            description
                                                "Number of times that the quic-tracker blocked flow creation due to
                                                 the initial IP packet of the flow not being the expected protocol.";
                                        }

                                    } // container blocked

                                    container closed {
                                        description "Enter the closed context";

                                        leaf invalid-quic {
                                            type yang:counter64;
                                            units "flows";
                                            description
                                                "Number of times that the quic-tracker closed flows due to the packet content
                                                 not being QUIC.";
                                        }

                                        leaf fragment-limit {
                                            type yang:counter64;
                                            units "flows";
                                            description
                                                "Number of times that the quic-tracker closed flows due to the number of message
                                                 fragments in the QUIC Init or Handshake messages exceeding the configured limit.";
                                        }

                                        leaf source-concurrent-handshake-limit {
                                            type yang:counter64;
                                            units "flows";
                                            description
                                                "Number of times that the quic-tracker closed flows due to the concurrent number
                                                 of quic flows in the handshake phase exceeding the configured source granularity
                                                 count policers.";
                                        }

                                        leaf concurrent-handshake-limit {
                                            type yang:counter64;
                                            units "flows";
                                            description
                                                "Number of times that the quic-tracker closed flows due to the concurrent number
                                                 of quic flows in the handshake phase exceeding the configured protected-object
                                                 granularity count policers.";
                                        }

                                        leaf application-data-guard-time {
                                            type yang:counter64;
                                            units "flows";
                                            description
                                                "Number of times that the quic-tracker closed flows due to the time between the
                                                 flow creation to the start of secure application data exceeding the configured
                                                 application data guard time.";
                                        }

                                        leaf inactivity {
                                            type yang:counter64;
                                            units "flows";
                                            description
                                                "Number of times that the quic-tracker closed flows due to the time between
                                                 packets exceeding the configured QUIC tracker (or UDP) inactivity timeout.";
                                        }

                                    } // container closed

                                } // container flows

                            } // container statistics

                        } // container summary

                    } // list quic-tracker

                    list sip-tracker {
                        key "sip-tracker-name";
                        description "Enter the sip-tracker list instance";

                        leaf sip-tracker-name {
                            type types-sros:named-item;
                            description "Specifies a name that uniquely identifies a sip-tracker within a DMS Protected Object.";
                        }

                        container summary {
                            description "Enter the summary context";

                            container statistics {
                                description "Enter the statistics context";

                                container events {
                                    description "Enter the events context";

                                    leaf dynamic-block {
                                        type yang:counter64;
                                        description "Number of times sip-tracker caused a source to transition to the dynamic-block state.";
                                    }

                                } // container events

                                container flows {
                                    description "Enter the flows context";

                                    container blocked {
                                        description "Enter the blocked context";

                                        leaf invalid-ip-protocol {
                                            type yang:counter64;
                                            units "flows";
                                            description
                                                "Number of times that the sip-tracker blocked flow creation due to
                                                 the initial IP packet of the flow not being the expected protocol.";
                                        }

                                    } // container blocked

                                    container udp {
                                        description "Enter the udp context";

                                        leaf created {
                                            type yang:counter64;
                                            units "flows";
                                            description "Number of SIP over UDP flows that the sip-tracker created.";
                                        }

                                        leaf created-mate {
                                            type yang:counter64;
                                            units "flows";
                                            description "Number of SIP over UDP mate flows created for this sip-tracker.";
                                        }

                                        container abandoned-protocol-tracking {
                                            description "Enter the abandoned-protocol-tracking context";

                                            leaf ip-fragment {
                                                type yang:counter64;
                                                units "flows";
                                                description
                                                    "Number of times that protocol tracking of a SIP session was abandoned due
                                                     to receipt of an IP fragment during payload protocol inspection.";
                                            }

                                        } // container abandoned-protocol-tracking

                                        container blocked {
                                            description "Enter the blocked context";

                                            leaf midstream {
                                                type yang:counter64;
                                                units "flows";
                                                description
                                                    "Number of times that the sip-tracker blocked flow creation due to the initial
                                                     packet being a SIP helper expected for midstream (STUN, keep-alive).";
                                            }

                                        } // container blocked

                                        container closed {
                                            description "Enter the closed context";

                                            leaf inactivity {
                                                type yang:counter64;
                                                units "flows";
                                                description
                                                    "Number of SIP over UDP flows that the sip-tracker closed due to the time between
                                                     packets exceeding the configured UDP inactivity timeout.";
                                            }

                                            leaf request-rate {
                                                type yang:counter64;
                                                units "flows";
                                                description
                                                    "Number of times that the sip-tracker closed UDP flows due to the sip request rate
                                                     exceeding the configured protected-object granularity request rate policers.";
                                            }

                                            leaf source-request-rate {
                                                type yang:counter64;
                                                units "flows";
                                                description
                                                    "Number of times that the sip-tracker closed UDP flows due to the sip request rate
                                                     exceeding the configured source granularity request rate policers.";
                                            }

                                            leaf invalid-sip {
                                                type yang:counter64;
                                                units "flows";
                                                description
                                                    "Number of times that the sip-tracker closed flows due to the packet content
                                                     not being SIP.";
                                            }

                                        } // container closed

                                    } // container udp


                                } // container flows

                            } // container statistics

                        } // container summary

                    } // list sip-tracker

                    list tls-tracker {
                        key "tls-tracker-name";
                        description "Enter the tls-tracker list instance";

                        leaf tls-tracker-name {
                            type types-sros:named-item;
                            description "Specifies a name that uniquely identifies a tls-tracker within a DMS Protected Object.";
                        }

                        container summary {
                            description "Enter the summary context";

                            container statistics {
                                description "Enter the statistics context";

                                container events {
                                    description "Enter the events context";

                                    leaf dynamic-block {
                                        type yang:counter64;
                                        description "Number of times tls-tracker caused a source to transition to the dynamic-block state.";
                                    }

                                } // container events

                                container flows {
                                    description "Enter the flows context";

                                    leaf created {
                                        type yang:counter64;
                                        units "flows";
                                        description "Number of times that a flow was created for this tls-tracker.";
                                    }

                                    leaf created-mate {
                                        type yang:counter64;
                                        units "flows";
                                        description "Number of times that a mate flow was created for this tls-tracker.";
                                    }

                                    container abandoned-protocol-tracking {
                                        description "Enter the abandoned-protocol-tracking context";

                                        leaf ip-fragment {
                                            type yang:counter64;
                                            units "flows";
                                            description
                                                "Number of times that protocol tracking of a TLS session was abandoned due
                                                 to receipt of an IP fragment during payload protocol inspection.";
                                        }

                                        leaf tolerance {
                                            type yang:counter64;
                                            units "flows";
                                            description
                                                "Number of times that protocol tracking of a TLS session was abandoned due
                                                 to receipt of a packet during payload protocol inspection that would have
                                                 been discarded, but was allowed under lenient tolerance.";
                                        }

                                    } // container abandoned-protocol-tracking

                                    container blocked {
                                        description "Enter the blocked context";

                                        leaf tcp-midstream {
                                            type yang:counter64;
                                            units "flows";
                                            description
                                                "Number of times that the tls-tracker blocked flow creation due to
                                                 the initial TCP packet of the flow not having the Syn flag set.";
                                        }

                                        leaf tcp-syn-ack {
                                            type yang:counter64;
                                            units "flows";
                                            description
                                                "Number of times that the tls-tracker blocked flow creation due to
                                                 a TCP SYN-ACK received in the mitigation rule direction.";
                                        }

                                        leaf invalid-ip-protocol {
                                            type yang:counter64;
                                            units "flows";
                                            description
                                                "Number of times that the tls-tracker blocked flow creation due to
                                                 the initial IP packet of the flow not being the expected protocol.";
                                        }

                                    } // container blocked

                                    container closed {
                                        description "Enter the closed context";

                                        leaf incomplete-tcp-handshake {
                                            type yang:counter64;
                                            units "flows";
                                            description
                                                "Number of times that the tls-tracker closed flows due to an excessive time gap
                                                 between the initial TCP handshake Syn and subsequent Ack.";
                                        }

                                        leaf start-guard-time {
                                            type yang:counter64;
                                            units "flows";
                                            description
                                                "Number of times that the tls-tracker closed flows due to the time between the
                                                 TCP handshake and the TLS Client Hello exceeding the configured start guard time.";
                                        }

                                        leaf invalid-tls {
                                            type yang:counter64;
                                            units "flows";
                                            description
                                                "Number of times that the tls-tracker closed flows due to the packet content
                                                 not being TLS.";
                                        }

                                        leaf client-hello-out-of-sequence {
                                            type yang:counter64;
                                            units "flows";
                                            description
                                                "Number of times that the tls-tracker closed flows due to the client hello
                                                 TCP segments being out of sequence.";
                                        }

                                        leaf client-cipher-limit {
                                            type yang:counter64;
                                            units "flows";
                                            description
                                                "Number of times that the tls-tracker closed flows due to the number of cipher
                                                 suites specified in the TLS Client Hello exceeding the configured limit.";
                                        }

                                        leaf client-extension-limit {
                                            type yang:counter64;
                                            units "flows";
                                            description
                                                "Number of times that the tls-tracker closed flows due to the number of TLS
                                                 extensions in the TLS Client Hello exceeding the configured limit.";
                                        }

                                        leaf tls-client-filter {
                                            type yang:counter64;
                                            units "flows";
                                            description
                                                "Number of times that the tls-tracker closed flows due to the TLS client
                                                 hello being discarded by the TLS client filter.";
                                        }

                                        leaf source-concurrent-handshake-limit {
                                            type yang:counter64;
                                            units "flows";
                                            description
                                                "Number of times that the tls-tracker closed flows due to the concurrent number
                                                 of tls flows in the handshake phase exceeding the configured source granularity
                                                 count policers.";
                                        }

                                        leaf concurrent-handshake-limit {
                                            type yang:counter64;
                                            units "flows";
                                            description
                                                "Number of times that the tls-tracker closed flows due to the concurrent number
                                                 of tls flows in the handshake phase exceeding the configured protected-object
                                                 granularity count policers.";
                                        }

                                        leaf handshake-out-of-sequence {
                                            type yang:counter64;
                                            units "flows";
                                            description
                                                "Number of times that the tls-tracker closed flows due to the security handshake
                                                 TCP segments being out of sequence.";
                                        }

                                        leaf handshake-guard-time {
                                            type yang:counter64;
                                            units "flows";
                                            description
                                                "Number of times that the tls-tracker closed flows due to the time between the
                                                 beginning of the security handshake and the end exceeding the configured handshake
                                                 guard time.";
                                        }

                                        leaf application-data-guard-time {
                                            type yang:counter64;
                                            units "flows";
                                            description
                                                "Number of times that the tls-tracker closed flows due to the time between the
                                                 end of the security handshake to the start of secure application data exceeding
                                                 the configured application data guard time.";
                                        }

                                        leaf tcp-protocol-violation {
                                            type yang:counter64;
                                            units "flows";
                                            description "Number of times that the tls-tracker closed flows due to a TCP protocol violation.";
                                        }

                                        leaf inactivity {
                                            type yang:counter64;
                                            units "flows";
                                            description
                                                "Number of times that the tls-tracker closed flows due to the time between
                                                 packets exceeding the configured TLS tracker (or TCP) inactivity timeout.";
                                        }

                                        leaf interrupted {
                                            type yang:counter64;
                                            units "flows";
                                            description "Number of times that the tls-tracker closed flows after having seen a TCP RST.";
                                        }

                                        leaf completed {
                                            type yang:counter64;
                                            units "flows";
                                            description "Number of times that the tls-tracker closed flows after having seen a TCP FIN.";
                                        }

                                    } // container closed

                                } // container flows

                            } // container statistics

                        } // container summary

                    } // list tls-tracker

                    container any-tracker {
                        description "Enter the any-tracker context";

                        container summary {
                            description "Enter the summary context";

                            container statistics {
                                description "Enter the statistics context";

                                container events {
                                    description "Enter the events context";

                                    leaf dynamic-block {
                                        type yang:counter64;
                                        description "Number of times any-tracker caused a source to transition to the dynamic-block state.";
                                    }

                                } // container events

                                container flows {
                                    description "Enter the flows context";

                                    container udp {
                                        description "Enter the udp context";

                                        leaf created {
                                            type yang:counter64;
                                            units "flows";
                                            description "Number of UDP flows that the generic any flow tracker created.";
                                        }

                                        leaf created-mate {
                                            type yang:counter64;
                                            units "flows";
                                            description "Number of UDP mate flows created for this any-tracker.";
                                        }

                                        container closed {
                                            description "Enter the closed context";

                                            leaf inactivity {
                                                type yang:counter64;
                                                units "flows";
                                                description
                                                    "Number of UDP flows that the generic any flow tracker closed due to the time between
                                                     packets exceeding the configured UDP inactivity timeout.";
                                            }

                                        } // container closed

                                    } // container udp

                                    container tcp {
                                        description "Enter the tcp context";

                                        leaf created {
                                            type yang:counter64;
                                            units "flows";
                                            description "Number of TCP flows that the generic any flow tracker created.";
                                        }

                                        leaf created-mate {
                                            type yang:counter64;
                                            units "flows";
                                            description "Number of TCP mate flows created for this any-tracker.";
                                        }

                                        container blocked {
                                            description "Enter the blocked context";

                                            leaf midstream {
                                                type yang:counter64;
                                                units "flows";
                                                description
                                                    "Number of times that the any-tracker blocked flow creation due to
                                                     the initial TCP packet of the flow not having the Syn flag set.";
                                            }

                                            leaf syn-ack {
                                                type yang:counter64;
                                                units "flows";
                                                description
                                                    "Number of times that the any-tracker blocked flow creation due to
                                                     a TCP SYN-ACK received in the mitigation rule direction.";
                                            }

                                        } // container blocked

                                        container closed {
                                            description "Enter the closed context";

                                            leaf incomplete-handshake {
                                                type yang:counter64;
                                                units "flows";
                                                description
                                                    "Number of TCP flows that the generic any flow tracker closed due to an excessive time gap
                                                     between the initial TCP handshake Syn and subsequent Ack.";
                                            }

                                            leaf start-guard-time {
                                                type yang:counter64;
                                                units "flows";
                                                description
                                                    "Number of times that the generic any flow tracker closed flows due to the time between the
                                                     TCP handshake and the subsequent TCP payload exceeding the configured start guard time.";
                                            }

                                            leaf protocol-violation {
                                                type yang:counter64;
                                                units "flows";
                                                description "Number of TCP flows that the generic any flow tracker closed due to a TCP protocol violation.";
                                            }

                                            leaf inactivity {
                                                type yang:counter64;
                                                units "flows";
                                                description
                                                    "Number of TCP flows that the generic any flow tracker closed due to the time between
                                                     packets exceeding the configured TCP inactivity timeout.";
                                            }

                                            leaf interrupted {
                                                type yang:counter64;
                                                units "flows";
                                                description "Number of TCP flows that the generic any flow tracker closed after having seen a TCP RST.";
                                            }

                                            leaf completed {
                                                type yang:counter64;
                                                units "flows";
                                                description "Number of TCP flows that the generic any flow tracker closed after having seen a TCP FIN.";
                                            }

                                        } // container closed

                                    } // container tcp

                                    container other {
                                        description "Enter the other context";

                                        leaf created {
                                            type yang:counter64;
                                            units "flows";
                                            description "Number of other flows (non TCP, non UDP) that the generic any flow tracker created.";
                                        }

                                        leaf created-mate {
                                            type yang:counter64;
                                            units "flows";
                                            description "Number of other mate flows created for this any-tracker.";
                                        }

                                        container closed {
                                            description "Enter the closed context";

                                            leaf inactivity {
                                                type yang:counter64;
                                                units "flows";
                                                description
                                                    "Number of other flows (non TCP, non UDP) that the generic any flow tracker closed due
                                                     to the time between packets exceeding the configured inactivity timeout.";
                                            }

                                        } // container closed

                                    } // container other

                                } // container flows

                            } // container statistics

                        } // container summary

                    } // container any-tracker

                    list tls-client-filter {
                        key "tls-client-filter-name";
                        description "Enter the tls-client-filter list instance";

                        leaf tls-client-filter-name {
                            type types-sros:named-item;
                            description "Specifies a name that uniquely identifies a tls-client-filter within a DMS Protected Object.";
                        }

                        list entry {
                            key "id";
                            description "Enter the entry list instance";

                            leaf id {
                                type uint32 {
                                    range "1..8";
                                }
                                description
                                    "Uniquely identifies the TLS client filter entry within the protected object TLS.
                                     client filter.  Lower entry numbers take precedence.";
                            }

                            container summary {
                                description "Enter the summary context";

                                container statistics {
                                    description "Enter the statistics context";

                                    leaf match {
                                        type yang:counter64;
                                        description "Number of matches to this client-filter entry which took the configured action.";
                                    }

                                } // container statistics

                            } // container summary

                        } // list entry

                        list esa {
                            key "esa-id vm";
                            description "Enter the esa list instance";

                            leaf esa-id {
                                type leafref {
                                    path "../../../../../../esa/esa-id";
                                }
                                description "Specifies an ESA identifier.";
                            }

                            leaf vm {
                                type leafref {
                                    path "../../../../../../esa[esa-id=current()/../esa-id]/vm/vm-id";
                                }
                                description "Specifies the VM identifier within the ESA.";
                            }

                            leaf oper-state {
                                type types-sros:oper-state;
                                description "Specifies the operational state of the tls client-filter.";
                            }

                            leaf oper-flags {
                                type types-dms:tls-client-filter-oper-flags-type;
                                description "The different conditions that affect the operating status of tls client-filter.";
                            }

                            container statistics {
                                description "Enter the statistics context";

                                leaf default-action {
                                    type yang:counter64;
                                    description
                                        "Number of times that none of the filter entries matched and the
                                         default-action was taken for this tls-client-filter.";
                                }

                            } // container statistics

                        } // list esa

                        container summary {
                            description "Enter the summary context";

                            leaf oper-state {
                                type types-sros:oper-state;
                                description "Specifies the operational state of the tls client-filter.";
                            }

                            leaf oper-flags {
                                type types-dms:tls-client-filter-oper-flags-type;
                                description "The different conditions that affect the operating status of tls client-filter.";
                            }

                            container statistics {
                                description "Enter the statistics context";

                                leaf default-action {
                                    type yang:counter64;
                                    description
                                        "Number of times that none of the filter entries matched and the
                                         default-action was taken for this tls-client-filter.";
                                }

                            } // container statistics

                        } // container summary

                    } // list tls-client-filter

                } // container protocol-handlers

                container mitigation-rules {
                    description "Enter the mitigation-rules context";

                    list entry {
                        key "id";
                        description "Enter the entry list instance";

                        leaf id {
                            type uint32 {
                                range "1..65535";
                            }
                            description "Uniquely identifies the mitigation rule within the protected object.";
                        }

                        container summary {
                            description "Enter the summary context";

                            container statistics {
                                description "Enter the statistics context";

                                container client-authentication {
                                    description "Enter the client-authentication context";

                                    container discard {
                                        description "Enter the discard context";

                                        leaf octets {
                                            type yang:counter64;
                                            units "bytes";
                                            description "Number of bytes discarded by client-authentication actions of this mitigation rule.";
                                        }

                                        leaf packets {
                                            type yang:counter64;
                                            units "packets";
                                            description "Number of packets discarded by client-authentication actions of this mitigation rule.";
                                        }

                                    } // container discard

                                    container events {
                                        description "Enter the events context";

                                        leaf attempt {
                                            type yang:counter64;
                                            units "bytes";
                                            description "Number of times that unauthenticated sources started a client authentication in this mitigation rule.";
                                        }

                                        leaf success {
                                            type yang:counter64;
                                            units "packets";
                                            description "Number of times that a client authentication was successfully completed in this mitigation rule.";
                                        }

                                    } // container events

                                    container replies-generated {
                                        description "Enter the replies-generated context";

                                        leaf octets {
                                            type yang:counter64;
                                            units "bytes";
                                            description "Number of bytes generated as server replies by client-authentication actions of this mitigation rule.";
                                        }

                                        leaf packets {
                                            type yang:counter64;
                                            units "packets";
                                            description "Number of packets generated as server replies by client-authentication actions of this mitigation rule.";
                                        }

                                    } // container replies-generated

                                } // container client-authentication

                                container discard {
                                    description "Enter the discard context";

                                    leaf octets {
                                        type yang:counter64;
                                        units "bytes";
                                        description
                                            "Number of bytes discarded by actions of this mitigation rule.
                                             These do not include the bytes discarded by client authentication.";
                                    }

                                    leaf packets {
                                        type yang:counter64;
                                        units "packets";
                                        description
                                            "Number of packets discarded by actions of this mitigation rule.
                                             These do not include the packets discarded by client authentication.";
                                    }

                                } // container discard

                                container match {
                                    description "Enter the match context";

                                    leaf hit {
                                        type yang:counter64;
                                        description
                                            "Number of times this mitigation rule matched a potential flow
                                                and all of the actions were applied.";
                                    }

                                    leaf conflict {
                                        type yang:counter64;
                                        description
                                            "Number of times this mitigation rule matched a potential flow
                                                and the actions were not applied due to a conflict with actions
                                                from an earlier rule.";
                                    }

                                } // container match

                                container mate-flows {
                                    description "Enter the mate-flows context";

                                    container discard {
                                        description "Enter the discard context";

                                        leaf octets {
                                            type yang:counter64;
                                            units "bytes";
                                            description
                                                "Number of bytes discarded by mate flows closed due to
                                                 actions of this mitigation rule.";
                                        }

                                        leaf packets {
                                            type yang:counter64;
                                            units "packets";
                                            description
                                                "Number of packets discarded by mate flows closed due to
                                                 actions of this mitigation rule.";
                                        }

                                    } // container discard

                                } // container mate-flows

                            } // container statistics

                        } // container summary

                    } // list entry


                } // container mitigation-rules

                container pre-filter {
                    description "Enter the pre-filter context";

                    container summary {
                        description "Enter the summary context";

                        container statistics {
                            description "Enter the statistics context";

                            container admit {
                                description "Enter the admit context";

                                leaf octets {
                                    type yang:counter64;
                                    units "bytes";
                                    description
                                        "Number of inbound bytes admitted by the genome-list pre-filter.  The packet
                                         source IP did not match any of the genome-lists that are configured
                                         to drop within the context of a Protected Object.";
                                }

                                leaf packets {
                                    type yang:counter64;
                                    units "packets";
                                    description
                                        "Number of inbound packets admitted by the genome-list pre-filter.  The packet
                                         source IP did not match any of the genome-lists that are configured
                                         to drop within the context of a Protected Object.";
                                }

                            } // container admit

                            container bypass {
                                description "Enter the bypass context";

                                leaf octets {
                                    type yang:counter64;
                                    units "bytes";
                                    description
                                        "Number of inbound bytes that bypassed mitigation-rules by the genome-list pre-filter.
                                         The packet source IP did match one or more genome-lists that are configured
                                         to bypass within the context of a Protected Object.";
                                }

                                leaf packets {
                                    type yang:counter64;
                                    units "packets";
                                    description
                                        "Number of inbound packets that bypassed mitigation-rules by the genome-list pre-filter.
                                         The packet source IP did match one or more genome-lists that are configured
                                         to bypass within the context of a Protected Object.";
                                }

                            } // container bypass

                            container deny {
                                description "Enter the deny context";

                                leaf octets {
                                    type yang:counter64;
                                    units "bytes";
                                    description
                                        "Number of inbound bytes denied by the genome-list pre-filter.  The packet
                                         source IP did match one or more genome-lists that are configured
                                         to drop within the context of a Protected Object.";
                                }

                                leaf packets {
                                    type yang:counter64;
                                    units "packets";
                                    description
                                        "Number of inbound packets denied by the genome-list pre-filter.  The packet
                                         source IP did match one or more genome-lists that are configured
                                         to drop within the context of a Protected Object.";
                                }

                            } // container deny

                            container outbound {
                                description "Enter the outbound context";

                                container admit {
                                    description "Enter the admit context";

                                    leaf octets {
                                        type yang:counter64;
                                        units "bytes";
                                        description
                                            "Number of outbound bytes admitted by the genome-list pre-filter.  The packet
                                             source IP did not match any of the genome-lists that are configured
                                             to drop within the context of a Protected Object.";
                                    }

                                    leaf packets {
                                        type yang:counter64;
                                        units "packets";
                                        description
                                            "Number of outbound packets admitted by the genome-list pre-filter.  The packet
                                             source IP did not match any of the genome-lists that are configured
                                             to drop within the context of a Protected Object.";
                                    }

                                } // container admit

                                container bypass {
                                    description "Enter the bypass context";

                                    leaf octets {
                                        type yang:counter64;
                                        units "bytes";
                                        description
                                            "Number of outbound bytes that bypassed mitigation-rules by the genome-list pre-filter.
                                             The packet source IP did match one or more genome-lists that are configured
                                             to bypass within the context of a Protected Object.";
                                    }

                                    leaf packets {
                                        type yang:counter64;
                                        units "packets";
                                        description
                                            "Number of outbound packets that bypassed mitigation-rules by the genome-list pre-filter.
                                             The packet source IP did match one or more genome-lists that are configured
                                             to bypass within the context of a Protected Object.";
                                    }

                                } // container bypass

                                container deny {
                                    description "Enter the deny context";

                                    leaf octets {
                                        type yang:counter64;
                                        units "bytes";
                                        description
                                            "Number of outbound bytes denied by the genome-list pre-filter.  The packet
                                             source IP did match one or more genome-lists that are configured
                                             to drop within the context of a Protected Object.";
                                    }

                                    leaf packets {
                                        type yang:counter64;
                                        units "packets";
                                        description
                                            "Number of outbound packets denied by the genome-list pre-filter.  The packet
                                             source IP did match one or more genome-lists that are configured
                                             to drop within the context of a Protected Object.";
                                    }

                                } // container deny

                            } // container outbound

                        } // container statistics

                    } // container summary

                    list genome-list {
                        key "id";
                        description "Enter the genome-list list instance";

                        leaf id {
                            type types-dms:genome-list;
                        }

                        container summary {
                            description "Enter the summary context";

                            container statistics {
                                description "Enter the statistics context";

                                container deny {
                                    status obsolete;
                                    description "Enter the deny context";

                                    leaf octets {
                                        status obsolete;
                                        type yang:counter64;
                                        units "bytes";
                                        description
                                            "Number of bytes denied that matched a specific pre-filter genome-list
                                             within the context of a Protected Object.";
                                    }

                                    leaf packets {
                                        status obsolete;
                                        type yang:counter64;
                                        units "packets";
                                        description
                                            "Number of packets denied that matched a specific pre-filter genome-list
                                             within the context of a Protected Object.";
                                    }

                                } // container deny

                                container match {
                                    description "Enter the match context";

                                    leaf octets {
                                        type yang:counter64;
                                        units "bytes";
                                        description
                                            "Number of inbound bytes that matched a specific pre-filter genome-list and
                                             took the configured action within the context of a Protected Object.";
                                    }

                                    leaf packets {
                                        type yang:counter64;
                                        units "packets";
                                        description
                                            "Number of inbound packets that matched a specific pre-filter genome-list and
                                             took the configured action within the context of a Protected Object.";
                                    }

                                } // container match

                                container outbound {
                                    description "Enter the outbound context";

                                    container match {
                                        description "Enter the match context";

                                        leaf octets {
                                            type yang:counter64;
                                            units "bytes";
                                            description
                                                "Number of outbound bytes that matched a specific pre-filter genome-list and
                                                 took the configured action within the context of a Protected Object.";
                                        }

                                        leaf packets {
                                            type yang:counter64;
                                            units "packets";
                                            description
                                                "Number of outbound packets that matched a specific pre-filter genome-list and
                                                 took the configured action within the context of a Protected Object.";
                                        }

                                    } // container match

                                } // container outbound

                            } // container statistics

                        } // container summary

                    } // list genome-list

                } // container pre-filter

            } // list protected-object

        } // container defender-mitigation-system

    } // grouping state-dms-defender-mitigation-system

}
