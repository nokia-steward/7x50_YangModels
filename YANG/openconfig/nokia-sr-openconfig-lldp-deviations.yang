module nokia-sr-openconfig-lldp-deviations {

    namespace "urn:nokia.com:sros:ns:yang:sr:openconfig-lldp-deviations";

    prefix "nokia-oc-lldp-devs";

    import nokia-sros-yang-extensions     { prefix "sros-ext"; }
    import openconfig-lldp                { prefix "oc-lldp"; }

    sros-ext:sros-major-release "rel26";
    organization "Nokia";
    contact
        "Nokia SR OS Support
         Web: <http://www.nokia.com>";
    description
        "This module contains the list of deviations against the openconfig-lldp
         module for the Nokia SR OS based routers.

         Copyright 2016 Nokia. All rights reserved. Reproduction of this document
         is authorized on the condition that the foregoing copyright notice is included.

         This nokia-sr-openconfig-lldp-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    deviation /oc-lldp:lldp/oc-lldp:config/oc-lldp:hello-timer {
        deviate replace {
            type uint64 {
                range "5..32768";
            }
        }
    }

    deviation /oc-lldp:lldp/oc-lldp:config/oc-lldp:system-name {
        deviate not-supported;
    }

    deviation /oc-lldp:lldp/oc-lldp:config/oc-lldp:system-description {
        deviate not-supported;
    }

    deviation /oc-lldp:lldp/oc-lldp:config/oc-lldp:chassis-id {
        deviate not-supported;
    }

    deviation /oc-lldp:lldp/oc-lldp:config/oc-lldp:chassis-id-type {
        deviate not-supported;
    }

    deviation /oc-lldp:lldp/oc-lldp:state/oc-lldp:hello-timer {
        deviate replace {
            type uint64 {
                range "5..32768";
            }
        }
    }

    deviation /oc-lldp:lldp/oc-lldp:state/oc-lldp:counters/oc-lldp:frame-in {
        deviate not-supported;
    }

    deviation /oc-lldp:lldp/oc-lldp:state/oc-lldp:counters/oc-lldp:frame-out {
        deviate not-supported;
    }

    deviation /oc-lldp:lldp/oc-lldp:state/oc-lldp:counters/oc-lldp:frame-error-in {
        deviate not-supported;
    }

    deviation /oc-lldp:lldp/oc-lldp:state/oc-lldp:counters/oc-lldp:frame-discard {
        deviate not-supported;
    }

    deviation /oc-lldp:lldp/oc-lldp:state/oc-lldp:counters/oc-lldp:tlv-discard {
        deviate not-supported;
    }

    deviation /oc-lldp:lldp/oc-lldp:state/oc-lldp:counters/oc-lldp:tlv-unknown {
        deviate not-supported;
    }

    deviation /oc-lldp:lldp/oc-lldp:state/oc-lldp:counters/oc-lldp:last-clear {
        deviate not-supported;
    }

    deviation /oc-lldp:lldp/oc-lldp:state/oc-lldp:counters/oc-lldp:tlv-accepted {
        deviate not-supported;
    }

    deviation /oc-lldp:lldp/oc-lldp:interfaces/oc-lldp:interface/oc-lldp:state/oc-lldp:counters/oc-lldp:last-clear {
        deviate not-supported;
    }

    deviation /oc-lldp:lldp/oc-lldp:interfaces/oc-lldp:interface/oc-lldp:neighbors/oc-lldp:neighbor/oc-lldp:custom-tlvs {
        deviate not-supported;
    }

}
