module nokia-sr-openconfig-messages-deviations {

    namespace "urn:nokia.com:sros:ns:yang:sr:openconfig-messages-deviations";

    prefix "nokia-oc-sys-msg-devs";

    import nokia-sros-yang-extensions     { prefix "sros-ext"; }
    import openconfig-messages            { prefix "oc-sys-msg"; }
    import openconfig-system              { prefix "oc-sys"; }

    sros-ext:sros-major-release "rel26";
    organization "Nokia";
    contact
        "Nokia SR OS Support
         Web: <http://www.nokia.com>";
    description
        "This module contains the list of deviations against the openconfig-messages
         module for the Nokia SR OS based routers.

         Copyright 2016 Nokia. All rights reserved. Reproduction of this document
         is authorized on the condition that the foregoing copyright notice is included.

         This nokia-sr-openconfig-messages-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    deviation /oc-sys:system/oc-sys:messages/oc-sys:state/oc-sys:message/oc-sys:msg {
        description "Added limit to string length.";
        deviate replace {
            type string {
                length "0..4100";
            }
        }
    }

    deviation /oc-sys-msg:messages {
        deviate not-supported;
    }

}
