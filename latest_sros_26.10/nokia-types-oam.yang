module nokia-types-oam {

    yang-version "1.1";

    namespace "urn:nokia.com:sros:ns:yang:sr:types-oam";

    prefix "types-oam";

    import ietf-yang-types                { prefix "yang"; }
    import nokia-sros-yang-extensions     { prefix "sros-ext"; }

    sros-ext:sros-major-release "rel26";
    organization "Nokia";
    contact
        "Nokia SR OS Support
         Web: <http://www.nokia.com>";
    description
        "Common OAM and Service Assurance Agent (SAA) type definitions data types used in the SR OS management system.

         Copyright 2016 Nokia. All rights reserved. Reproduction of this document
         is authorized on the condition that the foregoing copyright notice is included.

         This nokia-types-oam YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    typedef saa-threshold-direction {
        type enumeration {
            enum inbound                        { value 1; }
            enum outbound                       { value 2; }
            enum round-trip                     { value 3; }
        }
        description "An SAA threshold is configured against a packet flow direction.";
    }

    typedef test-result {
        type enumeration {
            enum undetermined                   { value 0; }
            enum success                        { value 1; }
            enum failed                         { value 2; }
            enum aborted                        { value 3; }
            enum transmission-resources-unavailable { value 4; }
        }
        description
            "Describes the result of a ping or trace test run.
             This is the YANG version of TmnxOamTestResult.
             Code points:
                 undetermined             (0) The result is, as yet, unknown.
                 success                  (1) The test was successful.
                 failed                   (2) The test failed.
                 aborted                  (3) The test was terminated before completion.
                 transmission-resources-
                 unavailable              (4) The test did not start because transmit
                                              resources are unavailable.";
    }

    typedef padding-pattern {
        type union {
            type enumeration {
                enum sequential                     { value -1; }
            }
            type uint32 {
                range "0..65535";
            }
        }
        default "sequential";
    }

    typedef direction {
        type enumeration {
            enum forward                        { value 1; }
            enum backward                       { value 2; }
            enum round-trip                     { value 3; }
        }
        description "OAM-PM measurement direction";
    }

    typedef statistics-measurement-interval-duration {
        type enumeration {
            enum raw                            { value 1; }
            enum 15-mins                        { value 2; }
            enum 1-hour                         { value 3; }
            enum 1-day                          { value 4; }
            enum 5-mins                         { value 5; }
            enum 1-min                          { value 6; }
        }
        description "OAM-PM measurement interval duration or raw data";
    }

    typedef measurement-interval-duration {
        type enumeration {
            enum 15-mins                        { value 2; }
            enum 1-hour                         { value 3; }
            enum 1-day                          { value 4; }
            enum 5-mins                         { value 5; }
            enum 1-min                          { value 6; }
        }
        description "OAM-PM measurement interval duration";
    }

    typedef forwarding-class {
        type enumeration {
            enum be                             { value 0; }
            enum l2                             { value 1; }
            enum af                             { value 2; }
            enum l1                             { value 3; }
            enum h2                             { value 4; }
            enum ef                             { value 5; }
            enum h1                             { value 6; }
            enum nc                             { value 7; }
        }
        default "be";
        description "The forwarding class type for the session";
    }

    typedef dscp-resolve {
        type enumeration {
            enum resolve                        { value 1000; }
        }
        description "Default value for OAM-PM DSCP configuration field";
    }

    typedef sath-mm-ss-string {
        type string {
            length "5";
            pattern "[0-5][0-9]:[0-5][0-9]" {
                error-message "'sath-mm-ss-string' must be mm:ss with 00-59 for each field (e.g. 05:30)";
            }
        }
        description
            "String used to represent minutes and seconds in format 'mm:ss'.
                minutes range: 00..59
                seconds range: 00..59";
    }

    typedef response-status {
        type enumeration {
            enum response-received              { value 1; }
            enum unknown                        { value 2; }
            enum internal-error                 { value 3; }
            enum max-concurrent-limit-reached   { value 4; }
            enum request-timed-out              { value 5; }
            enum unknown-orig-sdp-id            { value 6; }
            enum down-orig-sdp-id               { value 7; }
            enum request-terminated             { value 8; }
            enum invalid-originator-id          { value 9; }
            enum invalid-responder-id           { value 10; }
            enum unknown-resp-sdp-id            { value 11; }
            enum down-resp-sdp-id               { value 12; }
            enum invalid-service-id             { value 13; }
            enum invalid-sdp                    { value 14; }
            enum down-service-sdp               { value 15; }
            enum no-service-egress-label        { value 16; }
            enum invalid-host-address           { value 17; }
            enum invalid-mac-address            { value 18; }
            enum invalid-lsp-name               { value 19; }
            enum mac-is-local                   { value 20; }
            enum far-end-unreachable            { value 21; }
            enum down-originator-id             { value 22; }
            enum down-responder-id              { value 23; }
            enum changed-responder-id           { value 24; }
            enum down-orig-svc-id               { value 25; }
            enum down-resp-svc-id               { value 26; }
            enum no-service-ingress-label       { value 27; }
            enum mismatch-cust-id               { value 28; }
            enum mismatch-svc-type              { value 29; }
            enum mismatch-svc-mtu               { value 30; }
            enum mismatch-svc-label             { value 31; }
            enum no-sdp-bound-to-svc            { value 32; }
            enum down-orig-sdp-binding          { value 33; }
            enum invalid-lsp-path-name          { value 34; }
            enum no-lsp-endpoint-addr           { value 35; }
            enum invalid-lsp-id                 { value 36; }
            enum down-lsp-path                  { value 37; }
            enum invalid-lsp-protocol           { value 38; }
            enum invalid-lsp-label              { value 39; }
            enum route-is-local                 { value 40; }
            enum no-route-to-dest               { value 41; }
            enum local-extranet-route           { value 42; }
            enum src-ip-in-bgp-vpn-route        { value 43; }
            enum src-ip-invalid                 { value 44; }
            enum bgp-daemon-busy                { value 45; }
            enum mcast-not-enabled              { value 46; }
            enum m-trace-no-s-g-flow            { value 47; }
            enum m-trace-sys-ip-not-cfg         { value 48; }
            enum no-fwd-entry-in-mfib           { value 49; }
            enum dns-name-not-found             { value 50; }
            enum no-socket                      { value 51; }
            enum socket-opt-vprn-id-fail        { value 52; }
            enum socket-opt-if-inex-fail        { value 53; }
            enum socket-opt-next-hop-fail       { value 54; }
            enum socket-opt-mtu-disc-fail       { value 55; }
            enum socket-opt-sndbuf-fail         { value 56; }
            enum socket-opt-hdrinc-fail         { value 57; }
            enum socket-opt-tos-fail            { value 58; }
            enum socket-opt-ttl-fail            { value 59; }
            enum bind-socket-fail               { value 60; }
            enum no-route-by-intf               { value 61; }
            enum no-intf                        { value 62; }
            enum no-local-ip                    { value 63; }
            enum sendto-fail                    { value 64; }
            enum rcvd-wrong-type                { value 65; }
            enum no-direct-interface            { value 66; }
            enum nexthop-unreachable            { value 67; }
            enum socket-opt-hw-time-stamp-fail  { value 68; }
            enum no-spoke-sdp-in-vll            { value 69; }
            enum far-end-vccv-not-supported     { value 70; }
            enum no-vc-egress-label             { value 71; }
            enum socket-opt-ip-session-fail     { value 72; }
            enum rcvd-wrong-size                { value 73; }
            enum dns-lookup-fail                { value 74; }
            enum no-ipv6-src-addr-on-intf       { value 75; }
            enum multipath-not-supported        { value 76; }
            enum nh-intf-name-not-found         { value 77; }
            enum ms-pw-invalid-reply-mode       { value 78; }
            enum ancp-no-ancp-string            { value 79; }
            enum ancp-no-subscriber             { value 80; }
            enum ancp-no-ancp-string-for-subscriber { value 81; }
            enum ancp-no-access-nodefor-ancp-string { value 82; }
            enum ancp-no-ancp-capability-negotiated { value 83; }
            enum ancp-other-test-in-progress    { value 84; }
            enum ancp-max-nbr-ancp-tests-in-progress { value 85; }
            enum spoke-sdp-oper-down            { value 86; }
            enum no-ms-pw-vccv-in-reply-dir     { value 87; }
            enum p2mp-lsp-name-or-inst-invalid  { value 88; }
            enum p2mp-lsp-s2-l-path-down        { value 89; }
            enum p2mp-lsp-s2-l-address-invalid  { value 90; }
            enum p2mp-lsp-not-operational       { value 91; }
            enum p2mp-lsp-tr-multiple-replies   { value 92; }
            enum invalid-mep-id                 { value 93; }
            enum multiple-replies               { value 94; }
            enum packet-size-too-big            { value 95; }
            enum gtp-ping-error                 { value 96; }
            enum gtp-ping-rsrc-unavailable      { value 97; }
            enum gtp-ping-dup-request           { value 98; }
            enum gtp-ping-clean-up-in-prog      { value 99; }
            enum invalid-interface              { value 100; }
            enum p2mp-lsp-not-found             { value 101; }
            enum eth-cfm-slm-in-loss            { value 102; }
            enum eth-cfm-slm-out-loss           { value 103; }
            enum eth-cfm-slm-unacknowledged     { value 104; }
            enum spoke-sdp-fec-no-bnd-found     { value 105; }
            enum mtrace-not-supported-p2mp      { value 106; }
            enum use-fec129-parameters          { value 107; }
            enum dns-server-unexpected-response { value 108; }
            enum dns-server-response-form-err   { value 109; }
            enum dns-server-response-serv-fail  { value 110; }
            enum dns-server-response-not-imp    { value 111; }
            enum dns-server-response-refused    { value 112; }
            enum send-fail-undefined-service-id { value 113; }
            enum send-fail-wrong-service-type   { value 114; }
            enum send-fail-subnetted-service    { value 115; }
            enum invalid-resp-service-id        { value 116; }
            enum admin-down-orig-sdp-bind       { value 117; }
            enum oper-down-resp-sdp-bind        { value 118; }
            enum admin-down-resp-sdp-bind       { value 119; }
            enum sdp-bind-vcid-mismatch         { value 120; }
            enum sdp-bind-type-mismatch         { value 121; }
            enum sdp-bind-vc-type-mismatch      { value 122; }
            enum sdp-bind-vlan-vc-tag-mismatch  { value 123; }
            enum admin-down-orig-svc            { value 124; }
            enum admin-down-resp-svc            { value 125; }
            enum admin-down-orig-sdp-id         { value 126; }
            enum admin-down-resp-sdp-id         { value 127; }
            enum m-trace-source-is-not-remote   { value 128; }
            enum invalid-virtual-router-id      { value 129; }
            enum ldp-prefix-is-local            { value 130; }
            enum source-ip-is-not-local         { value 131; }
            enum next-hop-ip-is-local           { value 132; }
            enum target-ip-is-local             { value 133; }
            enum invalid-control-plane-option   { value 134; }
            enum iom-revision-not-supported     { value 135; }
            enum invalid-source-mac-option      { value 136; }
            enum send-fail-spb-mgd-service      { value 137; }
            enum use-static-pw-parameters       { value 138; }
            enum type1-fec129-pw-not-supported  { value 139; }
            enum mpls-tp-lsp-path-not-operational { value 140; }
            enum invalid-static-mpls-tp-lsp     { value 141; }
            enum control-word-not-valid         { value 142; }
            enum pw-path-id-not-configured      { value 143; }
            enum not-supported-on-vc-switch-service { value 144; }
            enum sdp-far-end-not-supported      { value 145; }
            enum mpls-tp-lsp-path-shutdown      { value 146; }
            enum force-option-is-blocked        { value 147; }
            enum intf-for-lsp-path-is-not-operational { value 148; }
            enum ttl-expired                    { value 149; }
            enum network-unreachable            { value 150; }
            enum host-unreachable               { value 151; }
            enum bgp-label-prefix-is-local      { value 152; }
            enum bgp-label-prefix-unknown       { value 153; }
            enum ldp-prefix-unknown             { value 154; }
            enum l2tpv3-delivery-type-unsupported { value 155; }
            enum v-ping-peer-cv-no-lsp-ping     { value 156; }
            enum v-ping-peer-cc-no-ctrl-word    { value 157; }
            enum send-fail-evpn-cfgd-service    { value 158; }
            enum send-failed                    { value 159; }
            enum minimum-packet-size-not-met    { value 160; }
            enum invalid-target-fec-type        { value 161; }
            enum p2mp-lsp-ping-not-supported-on-mgmt-rtr { value 162; }
            enum ipv4-sdp-far-ends-only         { value 163; }
            enum vxlan-egr-bnd-svc-mismatch     { value 164; }
            enum vxlan-no-matching-tep          { value 165; }
            enum vxlan-evpn-unconfigured        { value 166; }
            enum ipv6-sdp-far-ends-not-supported { value 167; }
            enum oam-test-over-s-r-tun-not-supported { value 168; }
            enum send-fail-evpn-cfgd-pbb-service { value 169; }
            enum tx-port-down                   { value 170; }
            enum no-tx-port                     { value 171; }
            enum parent-admin-down              { value 172; }
            enum dest-mac-resolve-fail          { value 173; }
            enum vxlan-ip-v6-term-unsupported   { value 174; }
            enum ip-prefix-is-local             { value 175; }
            enum ip-prefix-unknown              { value 176; }
            enum gre-eth-brdgd-delvry-type-unsupported { value 177; }
            enum mtrace2-disabled               { value 178; }
            enum ipv6-tunneled-next-hop-unsupported { value 179; }
            enum sr-tunneled-next-hop-unsupported { value 180; }
            enum sr-te-tunneled-next-hop-unsupported { value 181; }
            enum next-hop-ip-is-subnet          { value 182; }
            enum ip-dest-and-next-hop-combo-unsupported { value 183; }
            enum resolved-ip-dst-src-combo-unsupported { value 184; }
            enum sr-policy-not-found            { value 185; }
            enum sr-policy-segment-list-not-found { value 186; }
            enum eth-cfm-unsupported-test-type  { value 187; }
            enum ip-prefix-invalid              { value 188; }
            enum bier-error                     { value 189; }
            enum path-dest-addr-type-mismatch   { value 190; }
            enum src-addr-type-mismatch         { value 191; }
            enum nh-addr-type-mismatch          { value 192; }
            enum invalid-router-instance        { value 193; }
            enum mtrace2-oper-down              { value 194; }
            enum invalid-igp-instance           { value 195; }
            enum p2mp-lsp-ping-rsvp-lsp-type-no-support { value 196; }
            enum gre-over-ipv6-no-support       { value 197; }
            enum p2mp-lsp-not-configured        { value 198; }
            enum sr-policy-path-not-programmed  { value 199; }
            enum sr-policy-not-found-for-candidate-path { value 200; }
            enum srv6-policy-not-found          { value 201; }
            enum srv6-policy-segment-list-not-found { value 202; }
        }
        description
            "An object of type TmnxOamResponseStatus indicates the status of an OAM
             Echo probe operation.

             response-received(1) - Operation completed successfully.
             unknown(2) - Operation failed due to unknown error.
             internal-error(3) - An implementation detected an error in its own
                processing that caused an operation to fail.
             max-concurrent-limit-reached(4) - The maximum number of concurrent active
                operations would have been exceeded if the corresponding operation
                was allowed.
             request-timed-out(5) - Operation failed to receive a valid reply within
                the time limit imposed on it.
             unknown-orig-sdp-id(6) - Invalid or non-existent originating SDP-ID.
             down-orig-sdp-id(7) - The originating SDP-ID is operationally down.
             request-terminated(8) - The OAM ping test was terminated by the manager
                before reply or timeout.
             invalid-originator-id(9) - The far-end replied with an invalid
                originator-ID error.
             invalid-responder-id(10) - The far-end replied with an invalid
                responder-ID error.
             unknown-resp-sdp-id(11) - The far-end replied with an invalid response
                SDP-ID error.
             down-resp-sdp-id(12) - The far-end replied with down (admin or oper)
                response SDP-ID.
             invalid-service-id(13) - Invalid or non-existent originator Service-ID
                (svc-ping).
             invalid-sdp(14) - Invalid or non-existent SDP for Service (svc-ping).
             down-service-sdp(15) - SDP for the Service is down.  (svc-ping).
             no-service-egress-label(16) - Non-existent Service egress label.
                (svc-ping).
             invalid-host-address(17) - The IP address for a host has been determined
                to be invalid.  Examples of this are broadcast or multicast
                addresses. (svc-ping).
             invalid-mac-address(18) - The MAC address specified has been determined
                to be invalid. (macPing).
             invalid-lsp-name(19) - The LSP name specified has been determined to be
                invalid. (lspPing).
             mac-is-local(20) - MAC Ping or Trace route not sent because the MAC
                address is on a local SAP or CPU. (MAC-Ping/MAC-TR).
             far-end-unreachable(21) - No route to the far end of the GRE SDP tunnel.
             down-originator-id(22) - The ping originator is operationally down.
             down-responder-id(23) - The ping responder is operationally down.
             changed-responder-id(24) - The ping responder-ID is changed.
             down-orig-svc-id(25) - Service on the originator side is operationally
                down. (svc-ping).
             down-resp-svc-id(26) - Service on the responder side is operationally
                down. (svc-ping).
             no-service-ingress-label(27) - Non-existent service ingress label.
                (svc-ping).
             mismatch-cust-id(28) - Service customer ID mismatch between originator
                and responder. (svc-ping).
             mismatch-svc-type(29) - Service type mismatch between originator and
                responder. (svc-ping).
             mismatch-svc-mtu(30) - Service MTU mismatch between originator and
                responder. (svc-ping).
             mismatch-svc-label(31) - Service label mismatch between originator and
                responder. (svc-ping).
             no-sdp-bound-to-svc(32) - No SDP bound to the service. (svc-ping).
             down-orig-sdp-binding(33) - SDP binding is down on the Originator side.
                (sdp-ping).
             invalid-lsp-path-name(34) - The LSP path name specified is invalid.
                (lsp-ping).
             no-lsp-endpoint-addr(35) - No LSP Endpoint address. (lsp-ping).
             invalid-lsp-id(36) - No active LSP path found. (lsp-ping).
             down-lsp-path(37) - LSP path is operationally down. (lsp-ping).
             invalid-lsp-protocol(38) - LSP Protocol is not supported or is invalid.
                (lsp-ping).
             invalid-lsp-label(39) - LSP label is invalid. (lsp-ping).
             route-is-local(40) - The route is a local route. (vprn-ping).
             no-route-to-dest(41) - There is no route to the destination.  (vprn-ping).
             local-extranet-route(42) - The route is a local extranet route.
                (vprn-ping).
             src-ip-in-bgp-vpn-route(43) - The source IP belongs to a BGP-VPN route.
                (vprn-ping).
             src-ip-invalid(44) - The source IP is invalid or there is no route to the
                source. (vprn-ping)
             bgp-daemon-busy(45) - The BGP routing daemon is busy; vprn route target
                information is not retrievable. (vprn-trace)
             mcast-not-enabled(46) - Multicast is not enabled. Multicast trace cannot
                be initiated. (mtrace)
             m-trace-no-s-g-flow(47) - No (*,G)/(S,G) flow on the router. Multicast trace
                cannot be initiated. (mtrace)
             m-trace-sys-ip-not-cfg(48) - System ip address not configured. It is used as
                the response address in the multicast trace query. (mtrace)
             no-fwd-entry-in-mfib(49) - No forwarding entry could be found for the
                specified source and destination address in the MFIB.  (mfib-ping).
             dns-name-not-found(50) -  The domain name specified in the DNS query does
                not exist.
             no-socket(51) - unable to get socket. (icmp-ping).
             socket-opt-vprn-id-fail(52) - unable to set SO_VPRNID for socket.
                (icmp-ping).
             socket-opt-if-inex-fail(53) -  unable to set IP_IFINDEX for socket.
                (icmp-ping).
             socket-opt-next-hop-fail(54) - unable to set IP_NEXT_HOP for socket.
                (icmp-ping).
             socket-opt-mtu-disc-fail(55) - unable to set IP_MTU_DISC for socket.
                (icmp-ping).
             socket-opt-sndbuf-fail(56) - unable to set SO_SNDBUF for socket.
                (icmp-ping).
             socket-opt-hdrinc-fail(57) - unable to set IP_HDRINCL for socket.
                (icmp-ping).
             socket-opt-tos-fail(58) - unable to set IP_TOS for socket. (icmp-ping).
             socket-opt-ttl-fail(59) - unable to set IP_TTL for socket. (icmp-ping).
             bind-socket-fail(60) - unable to bind socket. (icmp-ping).
             no-route-by-intf(61) - no route to destination via the specified
                interface. (icmp-ping).
             no-intf(62) - no interface specified. (icmp-ping).
             no-local-ip(63) - unable to find local IP address. (icmp-ping).
             sendto-fail(64) - sendto function failed. (icmp-ping).
             rcvd-wrong-type(65) - received packet of wrong ICMP type. (icmp-ping).
             no-direct-interface(66) - no direct interface to reach destination.
                (icmp-ping).
             nexthop-unreachable (67) - unable to reach the next-hop. (icmp-ping).
             socket-opt-hw-time-stamp-fail (68) - unable to set IP_TIM_TIME for socket.
                (icmp-ping).
             no-spoke-sdp-in-vll (69) - unable to find spoke-sdp given sdp-id:vc-id
                (vccv-ping).
             far-end-vccv-not-supported (70) - far end does not support the VCCV
                options.  (vccv-ping).
             no-vc-egress-label (71) - no VC egress label to send vccv-ping.
             socket-opt-ip-session-fail (72) - unable to set IP_SESSION for socket.
                (icmp-ping).
             rcvd-wrong-size(73) - received packet of wrong size. (icmp-ping).
             dns-lookup-fail (74) - DNS lookup failed. (icmp-ping).
             no-ipv6-src-addr-on-intf (75) - no IPv6 source on the interface (icmp-ping).
             multipath-not-supported (76) - downstream node does not support
                multipath.  (lsp-trace).
             nh-intf-name-not-found (77) - Given next-hop interface name not found.
                (lsp-ping/trace).
             ms-pw-invalid-reply-mode (78) - MS-PW switching node supports ip-routed
                reply mode only (vccv-ping).
             ancp-no-ancp-string (79) - ANCP string unknown to the system.
             ancp-no-subscriber (80) - subscriber unknown to the system.
             ancp-no-ancp-string-for-subscriber (81) - subscriber has no associated ANCP
                string.
             ancp-no-access-nodefor-ancp-string (82) - no access node is found for the
                given ANCP string.
             ancp-no-ancp-capability-negotiated (83) - ANCP capability not negotiated
                with the involved DSLAM.
             ancp-other-test-in-progress (84) - another ANCP test is running for this
                ANCP string.
             ancp-max-nbr-ancp-tests-in-progress (85) - max number of concurrent ANCP
                tests reached.
             spoke-sdp-oper-down (86) - spoke-sdp is operationally down (vccv-ping).
             no-ms-pw-vccv-in-reply-dir (87) - Switching node in MS-PW with no VCCV
                support in echo reply direction.
             p2mp-lsp-name-or-inst-invalid (88) - P2MP LSP name or instance provided is
                not valid.
             p2mp-lsp-s2-l-path-down (89) - LSP path to S2L is down.
             p2mp-lsp-s2-l-address-invalid (90) - One or more S2L address is not valid.
             p2mp-lsp-not-operational (91) - P2MP LSP is operationally down.
             p2mp-lsp-tr-multiple-replies (92) - Probe returned multiple responses.
                Result may be inconsistent.
             invalid-mep-id (93) - The user-configured MEP identifier is not valid.
             multiple-replies (94) - more than one reply received, when one was
                expected.
             packet-size-too-big (95) - The packet is larger than the network's MTU and
                cannot be fragmented. For ICMP-ping tests, this results from an
                ICMPv4 type 3 code 4 or ICMPv6 type 2 message.
             gtp-ping-error (96) - General GTP Ping Error.
             gtp-ping-rsrc-unavailable (97) - GTP Path management resource unavailable.
             gtp-ping-dup-request (98) - Duplicate request for the same peer.
             gtp-ping-clean-up-in-prog (99) - GTP Path management clean up in progress.
             invalid-interface (100) - The egress interface specified does not exist.
             p2mp-lsp-not-found (101) - The P2MP-LSP not found given LDP-ID or
                sender address.
             eth-cfm-slm-in-loss(102) - Synthetic Loss Measurement (SLM) probe lost in
                transit from far-end node to local agent.
             eth-cfm-slm-out-loss(103) - SLM probe lost on transmit from local agent to
                far-end node.
             eth-cfm-slm-unacknowledged(104) - SLM probe lost but unable to identify
                loss reason.
             spoke-sdp-fec-no-bnd-found(105) - Spoke-sdp-fec is invalid or has no
                associated SDP binding yet.
             mtrace-not-supported-p2mp(106) - mtrace not supported in base routing
                context when incoming interface is p2mp
             use-fec129-parameters(107) - specify FEC129 parameters for FEC129 PW
                instead of sdp-id:vc-id
             dns-server-unexpected-response(108) - nameserver unexpected response.
             dns-server-response-form-err(109) - nameserver responded with FORMERR.
             dns-server-response-serv-fail(110) - nameserver responded with SERVFAIL.
             dns-server-response-not-imp(111) - nameserver responded with NOTIMP.
             dns-server-response-refused(112) - nameserver responded with REFUSED.
             send-fail-undefined-service-id(113) - The OAM test cannot be performed
                because the associated service does not exist.
             send-fail-wrong-service-type(114) - The OAM test cannot be performed
                because the associated service is of the wrong type.
             send-fail-subnetted-service(115) - The OAM test cannot be performed
                on a service with a specified MAC subnet length.
             invalid-resp-service-id(116) - Invalid or non-existent responder
                Service-ID.
             admin-down-orig-sdp-bind(117) - SDP binding is administratively down on the
                originator side.
             oper-down-resp-sdp-bind(118) - SDP binding is operationally down on the
                responder side.
             admin-down-resp-sdp-bind(119) - SDP binding is administratively down on the
                responder side.
             sdp-bind-vcid-mismatch(120) - SDP binding VC ID mismatch between
                originator and responder.
             sdp-bind-type-mismatch(121) - SDP binding type mismatch between originator
                and responder.
             sdp-bind-vc-type-mismatch(122) - SDP binding VC type mismatch between
                originator and responder.
             sdp-bind-vlan-vc-tag-mismatch(123) - SDP binding VLAN VC tag mismatch
                between originator and responder.
             admin-down-orig-svc(124) - Service on the originator side is
                administratively down.
             admin-down-resp-svc(125) - Service on the responder side is
                administratively down.
             admin-down-orig-sdp-id(126) - The originating SDP-ID is administratively
                down.
             admin-down-resp-sdp-id(127) - The responding SDP-ID is administratively
                down.
             m-trace-source-is-not-remote(128) - The multicast trace route test cannot be
                performed because the source address is not remote.
             invalid-virtual-router-id(129) - The OAM test cannot be performed because
                the associated virtual router ID is invalid.
             ldp-prefix-is-local(130) - The OAM test cannot be performed because the
                associated LDP prefix is local to the system.
             source-ip-is-not-local(131) - The OAM test cannot be performed because the
                associated source address is not local to the system.
             next-hop-ip-is-local(132) - The OAM test cannot be performed because the
                associated next hop address is local to the system.
             target-ip-is-local(133) - The OAM test cannot be performed because the
                associated target address is local to the system.
             invalid-control-plane-option(134) - The OAM test cannot be performed
                because the control plane send or receive option is not allowed
                with the specified service.
             iom-revision-not-supported(135) - The OAM test cannot be performed due
                to a mismatch in supported revision with the provisioned IOMs.
             invalid-source-mac-option(136) - The OAM test cannot be performed because
                the source MAC option is not allowed with the specified service.
             send-fail-spb-mgd-service(137) - The OAM test cannot be performed on a
                service which is managed by SPB.
             use-static-pw-parameters(138) - The spoke SDP is configured for static PW.
             type1-fec129-pw-not-supported(139) - The OAM test is not supported on
                type 1 FEC129 pseudowires.
             mpls-tp-lsp-path-not-operational(140) - The OAM test cannot be performed
                because the MPLS-TP LSP path is not operational.
             invalid-static-mpls-tp-lsp(141)- The OAM test only supports static MPLS-TP
                LSPs.
             control-word-not-valid(142) - The control word for the spoke-sdp is not
                valid for this OAM test.
             pw-path-id-not-configured(143) - The pw-path-id provisioning is not
                complete.
             not-supported-on-vc-switch-service(144) - The OAM test is not supported on a
                vc-switching service.
             sdp-far-end-not-supported(145) - The OAM test does not support the SDP far
                end value.
             mpls-tp-lsp-path-shutdown(146) - The MPLS-TP path is currently shutdown.
             force-option-is-blocked(147) - The force option is currently blocked
                because of the configuration of a related entity.
             intf-for-lsp-path-is-not-operational(148) - The interface for the LSP path is
                not operational
             ttl-expired(149) - The destination could not be reached because the
                time-to-live (IPv4) or hop limit (IPv6) was too small. This
                results from an ICMPv4 type 11 code 0 or ICMPv6 type 3 code 0
                message.
             network-unreachable(150) - The network specified by the destination
                address is unreachable. This results from an ICMPv4 type 3 code 0
                or ICMPv6 type 1 code 0 message.
             host-unreachable(151) - The host specified by the destination address is
                unreachable. This results from an ICMPv4 type 3 code 1 or ICMPv6
                type 1 code 3 message.
             bgp-label-prefix-is-local(152) - The OAM test cannot be performed because
                the associated BGP Label Route prefix is local to the system.
             bgp-label-prefix-unknown(153) - The OAM test cannot be performed because
                the BGP Target FEC prefix entry is not found in the Routing Table.
             ldp-prefix-unknown(154) - The OAM test cannot be performed because the
                LDP Target FEC prefix entry is not found in the Routing Table.
             l2tpv3-delivery-type-unsupported(155) - The OAM test cannot be performed
                because the l2TPv3 delivery type is unsupported.
             v-ping-peer-cv-no-lsp-ping(156) - The OAM test cannot be performed because
                the peer CV bits do not support lsp ping.
             v-ping-peer-cc-no-ctrl-word(157) - The OAM test cannot be performed because
                the peer CC bits do not support control word.
             send-fail-evpn-cfgd-service(158) - The OAM test cannot be performed on a
                VPLS service that has EVPN configured.
             send-failed(159) - The OAM test cannot send the test packet.
             minimum-packet-size-not-met(160) - The OAM test cannot send the test packet
                as the minimum required packet size exceeds the user supplied packet
                size.
             invalid-target-fec-type(161) - The OAM test does not support this FEC
                type.
             p2mp-lsp-ping-not-supported-on-mgmt-rtr(162) - The OAM p2mpLspPing test is not
                supported on the management router.
             ipv4-sdp-far-ends-only(163) - The OAM test only supports bindings and SDPs
                using an IPv4 far end.
             vxlan-egr-bnd-svc-mismatch(164) - The OAM test cannot send packets to a
                VXLAN egress binding not owned by the same service as the one
                sending.
             vxlan-no-matching-tep(165) - The OAM test can only send to VTEPs that have
                been configured.
             vxlan-evpn-unconfigured(166) - The OAM test can only send on a service
                with EVPN configured.
             ipv6-sdp-far-ends-not-supported(167) - The OAM test does not support
                bindings and SDPs using an IPv6 far end.
             oam-test-over-s-r-tun-not-supported(168) - The OAM test is not supported on SR
                tunnels.
             send-fail-evpn-cfgd-pbb-service(169) - The OAM test cannot be performed on a
                VPLS/Epipe service that is associated with a b-vpls that has EVPN
                configured.
             tx-port-down(170) - The transmit port is operationally down.
             no-tx-port(171) - No transmit port.
             parent-admin-down(172) - The parent (SPOKE, SAP, service or port) of the
                MEP is administratively down.
             dest-mac-resolve-fail(173) - Unable to resolve the remote-mepid to a
                unicast layer2 MAC address.
             vxlan-ip-v6-term-unsupported(174) - The OAM test does not support IPv6
                tunnel termination points.
             ip-prefix-is-local(175) - The OAM test cannot be performed because
                the associated IP prefix is local to the system.
             ip-prefix-unknown(176) - The OAM test cannot be performed because the
                Target FEC prefix entry is not found in the Routing Table.
             gre-eth-brdgd-delvry-type-unsupported(177) - The OAM test cannot be
                performed because the GRE Ethernet Bridged delivery type is
                unsupported.
             mtrace2-disabled(178) - The mtrace2 test cannot be performed because
                mtrace2 is disabled at the system level.
             ipv6-tunneled-next-hop-unsupported(179) - The VPRN ping/trace test has
                no support for IPv6 tunneled next hops.
             sr-tunneled-next-hop-unsupported(180) - The VPRN ping/trace test has no
                support for Segment Routing tunneled next hops.
             sr-te-tunneled-next-hop-unsupported(181) - The VPRN ping/trace test has
                no support for Segment Routing Traffic Engineering next hops.
             next-hop-ip-is-subnet(182) - The OAM test cannot be performed because the
                associated next hop address is a subnet.
             ip-dest-and-next-hop-combo-unsupported(183) - The IP destination address
                type and provided next hop type is not a supported combination.
             resolved-ip-dst-src-combo-unsupported(184) - The resolved IP destination
                address type and provided source address type is not a supported
                combination.
             sr-policy-not-found(185) - The SR-POLICY not found given color and
                endpoint.
             sr-policy-segment-list-not-found(186) - The SR-POLICY's segment list not
                found given segment list Id.
             eth-cfm-unsupported-test-type(187) - The test type is not valid for the
                MEP.
             ip-prefix-invalid(188) - The OAM test cannot be performed because the
                Target FEC prefix entry is not valid for the test.
             bier-error (189) - The BIER OAM test received a reply with an
                unsuccessful return code.
             path-dest-addr-type-mismatch(190) - The path destination address type
                doesn't match the prefix address type.
             src-addr-type-mismatch(191) - The source address type doesn't match
                the prefix address type.
             nh-addr-type-mismatch(192) - The next hop address type doesn't match
                the prefix address type.
             invalid-router-instance(193) - a probe cannot be sent because the
                test's router-instance is invalid.
             mtrace2-oper-down(194) - An mtrace2 probe cannot be sent because
                mtrace2 is operationally down at the system level.
             invalid-igp-instance(195) - The OAM test cannot be performed because the
               IGP instance is not valid for the protocol.
             p2mp-lsp-ping-rsvp-lsp-type-no-support(196) - P2MP LSP Ping not supported on
               RSVP LSPs of type 'p2mp-lsp'.
             gre-over-ipv6-no-support(197) - The OAM test does not support GRE over IPv6.
             p2mp-lsp-not-configured(198) - The P2MP LSP not configured.
             sr-policy-path-not-programmed(199) - The SR-POLICY's path is not programmed.
             sr-policy-not-found-for-candidate-path(200) - The SR-POLICY is not found for
               given color, endpoint and candidate path.
             srv6-policy-not-found(201) - The SRv6-POLICY not found given color and
                endpoint.
             srv6-policy-segment-list-not-found(202) - The SRv6-POLICY's segment list not
                found given segment list Id.";
    }

    typedef ping-return-code {
        type enumeration {
            enum not-applicable                 { value 0; }
            enum fec-egress                     { value 1; }
            enum fec-no-map                     { value 2; }
            enum not-downstream                 { value 3; }
            enum downstream                     { value 4; }
            enum downstream-not-label           { value 5; }
            enum downstream-not-mac             { value 6; }
            enum downstream-not-mac-flood       { value 7; }
            enum malformed-echo-request         { value 8; }
            enum tlv-not-understood             { value 9; }
            enum downstream-not-in-mfib         { value 10; }
            enum downstream-mismatched          { value 11; }
            enum upstream-if-id-unkn            { value 12; }
            enum no-mpls-fwd                    { value 13; }
            enum no-label-at-stack-depth        { value 14; }
            enum proto-intf-mismatched          { value 15; }
            enum terminated-by-one-label        { value 16; }
            enum see-ddmap-for-ret-code-sub-code { value 17; }
            enum fec-stack-change               { value 18; }
        }
        description
            "ping-return-code indicates the return code received in the OAM ping response common
             header.

             Code points:
                not-applicable                    The return code has no significance in the
                                                   context of the test being conducted.
                fec-egress                        Replying router is an egress for the Forwarding
                                                   Equivalence Class (FEC).
                fec-no-map                        Replying router has no mapping for the FEC.
                not-downstream                    Replying router is not one of the
                                                   downstream routers.
                downstream                        Replying router is one of the downstream
                                                   routers and its mapping for this FEC on the
                                                   received interface is the given label.
                downstream-not-label              Replying router is one of the downstream
                                                   routers but its mapping for this FEC is not
                                                   the given label.
                downstream-not-mac                Replying router is one of the downstream
                                                   routers but it does not have the given MAC
                                                   address
                downstream-not-mac-flood          Replying router is one of the downstream
                                                   routers but it does not have the given MAC
                                                   address and is unable to flood the request.
                malformed-echo-request            A malformed echo request was received.
                tlv-not-understood                One or more of the TLVs was not understood.
                downstream-not-in-mfib            Replying router is one of the downstream
                                                   routers but it does not have an MFIB entry
                                                   for the given source group combination.
                downstream-mismatched             Downstream mapping mismatched.
                upstream-if-id-unkn               Upstream interface index unknown.
                no-mpls-fwd                       Label switched but no MPLS forwarding at
                                                   stack-depth.
                no-label-at-stack-depth           No label entry at stack-depth.
                proto-intf-mismatched             Protocol not associated with interface at
                                                   FEC stack-depth.
                terminated-by-one-label           Premature termination of ping due to
                                                   label stack shrinking to a single label.
                see-ddmap-for-ret-code-sub-code   See DDMap TLV for rc and sub-rc.
                fec-stack-change                  Label switched with FEC stack change.";
    }

    typedef lsp-ping-trace-return-code {
        type enumeration {
            enum no-return-code                 { value 0; }
            enum malformed-echo-request         { value 1; }
            enum tlv-not-understood             { value 2; }
            enum fec-egress                     { value 3; }
            enum fec-no-map                     { value 4; }
            enum downstream-mismatched          { value 5; }
            enum upstream-if-id-unkn            { value 6; }
            enum reserved                       { value 7; }
            enum fec-map-to-label               { value 8; }
            enum no-mpls-fwd                    { value 9; }
            enum fec-map-not-to-label           { value 10; }
            enum no-label-at-stack-depth        { value 11; }
            enum proto-intf-mismatched          { value 12; }
            enum terminated-by-one-label        { value 13; }
            enum see-ddmap-for-ret-code-sub-code { value 14; }
            enum fec-stack-change               { value 15; }
            enum downstream-not-mac             { value 16; }
            enum downstream-not-mac-flood       { value 17; }
            enum downstream-not-in-mfib         { value 18; }
        }
        description
            "RFC 8029/4379 Return Codes:

             The Return Code is set to zero by the sender of an echo request.  The
             receiver of said echo request can set it to one of the values listed
             below in the corresponding echo reply that it generates.  The
             notation <RSC> refers to the Return Subcode.  This field is filled in
             with the stack-depth for those codes that specify that.  For all
             other codes, the Return Subcode MUST be set to zero.
             Value    Meaning
             -----    -------
                 0    - No Return Code
                 1    - Malformed echo request received
                 2    - One or more of the TLVs was not understood
                 3    - Replying router is an egress for the FEC at stack-depth <RSC>
                 4    - Replying router has no mapping for the FEC at stack-depth <RSC>
                 5    - Downstream Mapping Mismatch (See Note 1)
                 6    - Upstream Interface Index Unknown (See Note 1)
                 7    - Reserved
                 8    - Label switched at stack-depth <RSC>
                 9    - Label switched but no MPLS forwarding at stack-depth <RSC>
                10    - Mapping for this FEC is not the given label at stack-depth <RSC>
                11    - No label entry at stack-depth <RSC>
                12    - Protocol not associated with interface at FEC stack-depth <RSC>
                13    - Premature termination of ping due to label stack shrinking to a single label
                14    - See DDMAP TLV for meaning of Return Code and Return Subcode (See Note 2)
                15    - Label switched with FEC change
                16    - Replying router is one of the downstream routers but it does not have
                        the given MAC address
                17    - Replying router is one of the downstream routers but it does not have
                        the given MAC address and is unable to flood the request
                18    - Replying router is one of the downstream routers but it does not have an MFIB entry
                        for the given source group combination";
    }

    typedef mpls-lsp-ping-return-code {
        type enumeration {
            enum no-return-code {
                value 0;
                description "No Return Code";
            }
            enum malformed-echo-request {
                value 1;
                description "Malformed echo request received";
            }
            enum tlv-not-understood {
                value 2;
                description "One or more of the TLVs was not understood";
            }
            enum fec-egress {
                value 3;
                description "Replying router is an egress for the FEC at stack-depth <RSC>";
            }
            enum fec-no-map {
                value 4;
                description "Replying router has no mapping for the FEC at stack-depth <RSC>";
            }
            enum downstream-mismatched {
                value 5;
                description "Downstream Mapping Mismatch";
            }
            enum upstream-if-id-unkn {
                value 6;
                description "Upstream Interface Index Unknown";
            }
            enum reserved {
                value 7;
                description "Reserved";
            }
            enum fec-map-to-label {
                value 8;
                description "Label switched at stack-depth <RSC>";
            }
            enum no-mpls-fwd {
                value 9;
                description "Label switched but no MPLS forwarding at stack-depth <RSC>";
            }
            enum fec-map-not-to-label {
                value 10;
                description "Mapping for this FEC is not the given label at stack-depth <RSC>";
            }
            enum no-label-at-stack-depth {
                value 11;
                description "No label entry at stack-depth <RSC>";
            }
            enum proto-intf-mismatched {
                value 12;
                description "Protocol not associated with interface at FEC stack-depth <RSC>";
            }
            enum terminated-by-one-label {
                value 13;
                description "Premature termination of ping due to label stack shrinking to a single label";
            }
            enum see-ddmap-for-ret-code-sub-code {
                value 14;
                description "See DDMAP TLV for meaning of Return Code and Return Subcode";
            }
            enum fec-stack-change {
                value 15;
                description "Label switched with FEC change";
            }
        }
        description
            "The return code provided in the header of an MPLS echo reply.

             The Return Code is set to zero by the sender of an echo request.  The
             receiver of said echo request can set it to one of the values listed
             below in the corresponding echo reply that it generates.  The
             notation <RSC> refers to the Return Subcode.  This field is filled in
             with the stack-depth for those codes that specify that.  For all
             other codes, the Return Subcode MUST be set to zero.

             RFC 8029 'Detecting Multi-Protocol Label Switched (MPLS) Data Plane Failures',
             section 3.1 Return Code.

             IANA has created and will maintain registries for Return Codes
             (see https://www.iana.org/assignments/mpls-lsp-ping-parameters/)
             but only the values 0 to 15 are currently supported.
             ";
    }

    typedef sath-hh-mm-ss-string {
        type string {
            length "8";
            pattern "([2][0-4]|[0-1][0-9]):[0-5][0-9]:[0-5][0-9]" {
                error-message "'sath-hh-mm-ss-string' must be hh:mm:ss with hours 00-24 and minutes/seconds 00-59";
            }
        }
        description
            "String used to represent hours, minutes, and seconds in format 'hh:mm:ss'.
                hours range:   00..24
                minutes range: 00..59
                seconds range: 00..59";
    }

    typedef twamp-server-connection-count {
        type uint32 {
            range "0..64";
        }
        description "The number of concurrent control connections supported by a TWAMP server";
    }

    typedef twamp-server-session-count {
        type uint32 {
            range "0..128";
        }
        description "The number of concurrent test sessions supported by a TWAMP server";
    }

    typedef twamp-timestamp-author {
        type enumeration {
            enum central                        { value 1; }
            enum fp                             { value 2; }
        }
        description "The entity which writes to the timestamp field of an outbound TWAMP or TWAMP-Light packet.";
    }

    typedef oam-pm-session-test-detected-tx-error {
        type enumeration {
            enum none                           { value 1; }
            enum port-down                      { value 2; }
            enum no-tx-port                     { value 3; }
            enum eth-parent-admin-down          { value 4; }
            enum eth-no-mep-or-admin-down       { value 5; }
            enum unexpected-error               { value 6; }
            enum no-service                     { value 7; }
            enum service-admin-down             { value 8; }
            enum service-oper-down              { value 9; }
            enum no-route                       { value 10; }
            enum no-interface                   { value 11; }
            enum no-direct-interface            { value 12; }
            enum source-interface-down          { value 13; }
            enum source-ip-not-local            { value 14; }
            enum next-hop-ip-is-local           { value 15; }
            enum dest-mac-resolve-fail          { value 16; }
            enum mpls-dm-system-disabled        { value 17; }
            enum lsp-not-available              { value 18; }
            enum lsp-oper-down                  { value 19; }
            enum udp-return-ip-not-local        { value 20; }
            enum eth-cfm-unsupported-test-type  { value 21; }
            enum srv6-tunnel-unavailable        { value 22; }
        }
        description
            "Reason for the inability (if any) to launch test frames for the specified test

             none                      (1) - no transmit failure has been detected
             port-down                 (2) - the transmit port is operationally down
             no-tx-port                (3) - an egress has not been found
             eth-parent-admin-down     (4) - the parent (e.g. the SAP, SDP, service, or port) of the MEP is administratively down
             eth-no-mep-or-admin-down  (5) - the test's MEP is not fully configured or the MEP is administratively down
             unexpected-error          (6) - transmission failed due to unexpected conditions, such as failed memory allocation,
                                             traffic congestion, or failure to obtain the necessary resources
             no-service                (7) - the service associated with this test session was not found
             service-admin-down        (8) - the service associated with this test session is administratively down
             service-oper-down         (9) - the service associated with this test session is operationally down
             no-route                 (10) - there is no IP route to the destination address
             no-interface             (11) - there is no IP interface that matches the configured forwarding interface
             no-direct-interface      (12) - there is no appropriate IP interface for bypass-routing to the destination address
             source-interface-down    (13) - the IP interface associated with the source address is down
             source-ip-not-local      (14) - the source address is not local
             next-hop-ip-is-local     (15) - the next-hop address is local
             dest-mac-resolve-fail    (16) - unable to resolve the remote-mepid to a unicast layer2 MAC address
             mpls-dm-system-disable   (17) - MPLS-DM disabled at system level
             lsp-not-available        (18) - LSP not available (e.g. not configured)
             lsp-oper-down            (19) - LSP is operationally down
             udp-return-ip-not-local  (20) - UDP Return IP address is not local
             eth-cfm-unsupported-test-type (21) - the test type is not valid on the MEP
             srv6-tunnel-unavailable  (22) - the segment-routing-v6 tunnel is not available
                                             (e.g. not configured, or down) ";
    }

    typedef oam-pm-session-test-liveness-oper-state {
        type enumeration {
            enum not-applicable                 { value 1; }
            enum no-threshold-config            { value 2; }
            enum oper-down                      { value 3; }
            enum idle                           { value 4; }
            enum active                         { value 5; }
            enum failed                         { value 6; }
        }
        description
            "Status of liveness monitoring for the test

             not-applicable(1)
                 - the test type (e.g. DMM) does not support liveness monitoring
             no-threshold-config(2)
                 - the test does not have a configured liveness failure threshold
             oper-down(3)
                 - the test is operationally down (includes administratively down)
             idle(4)
                 - the test is trying to send request packets, and zero replies have
                   been received
             active(5)
                 - the test has received one or more reply packets, and the test is
                   not 'failed'
             failed(6)
                 - the configured threshold for consecutive request/reply failures is met
                   (or exceeded)";
    }

    typedef oam-pm-session-mpls-dm-rx-status {
        type enumeration {
            enum success                        { value 1; }
            enum notif-data-format-invalid      { value 2; }
            enum notif-initialization-in-progress { value 3; }
            enum notif-data-reset-occurred      { value 4; }
            enum notif-resource-temporarily-unavail { value 5; }
            enum error-unspecified-error        { value 16; }
            enum error-unsupported-version      { value 17; }
            enum error-unsupported-control-code { value 18; }
            enum error-unsupported-data-format  { value 19; }
            enum error-authentication-failure   { value 20; }
            enum error-invalid-destination-node-id { value 21; }
            enum error-connection-mismatch      { value 22; }
            enum error-unsupported-mandtlv-object { value 23; }
            enum error-unsupported-query-interval { value 24; }
            enum error-administrative-block     { value 25; }
            enum error-resource-unavailable     { value 26; }
            enum error-resource-released        { value 27; }
            enum error-invalid-message          { value 28; }
            enum error-protocol-error           { value 29; }
            enum none                           { value 256; }
            enum error-timeout                  { value 257; }
        }
        description
            "The most recent receive status for an OAM-PM MPLS-DM test.

             A value less than 256 was copied from the Control Code field of
             the most recent MPLS-DM response message.  The value indicates
             whether or not the most recent query message (sent by this node as
             part of an MPLS-DM test) was processed successfully by the far-end
             node.

             'none(256)' is a proprietary code point, indicating the receive status
             is irrelevant or unknown (e.g. the test has not been started).

             'error-timeout(257)' is a proprietary code point, indicating the most
             recent receive event for a running test was an internal timeout,
             rather than the expected receipt of an MPLS-DM response message.";
    }

    typedef sath-statistics-test-run-oper-state {
        type enumeration {
            enum none                           { value 1; }
            enum running                        { value 2; }
            enum stopped-by-user                { value 3; }
            enum passed                         { value 4; }
            enum failed                         { value 5; }
            enum stopped-by-fault               { value 6; }
        }
        description
            "In the context of Service Activation TestHead (SATH):

             Indicates the operational state of a run for a service test, service stream, or test.

             stopped-by-fault indicates the service-test was stopped because
             a fatal error occurred.
             For example:
             1.  A CPM activity switch occurred after the test started.
             2.  The IOM hosting one of the service-test's service streams
                 was extracted.";
    }

    typedef sath-statistics-test-oper-state {
        type enumeration {
            enum unknown                        { value 1; }
            enum pass                           { value 2; }
            enum fail                           { value 3; }
        }
        description
            "In the context of Service Activation TestHead (SATH):

             Indicates the operational state of a test with respect to a particular acceptance
             criteria.";
    }

    typedef sath-loss-percent-decimal64 {
        type decimal64 {
            range "0.0000..100.0000";
            fraction-digits 4;
        }
        units "percent";
        description
            "A percentage that has four decimal places of specificity.

             Assumes -1 is used to indicate uninitialized percentage.";
    }

    typedef sath-positive-percent-four-decimal-places {
        type decimal64 {
            range "0.0000..100.0000";
            fraction-digits 4;
        }
        units "percent";
        default "0.0000";
        description "A percentage that has four decimal places of precision.";
    }

    typedef sath-loss-percent-union {
        type union {
            type sath-positive-percent-four-decimal-places;
            type enumeration {
                enum none                           { value -1; }
            }
        }
        description
            "A union of a decimal64 percentage that has four decimal places of specificity and an
             enumeration, 'none'.

             Assumes -1 is used to indicate no percentage and will be mapped to the enumeration.";
    }

    typedef sath-test-time-start {
        type union {
            type yang:date-and-time;
            type enumeration {
                enum not-started                    { value -1; }
            }
        }
        description
            "A type that accommodates a `yang:date-and-time` and an enumeration, 'not-started'. The
             typedef assumes that the start of the Unix epoch (1970/01/01 00:00:00.0) is a special
             value and is mapped the enumeration to show the test has not yet started. All other
             date values are treated as normal `yang:date-and-time`s.";
    }

    typedef sath-test-time-end {
        type union {
            type yang:date-and-time;
            type enumeration {
                enum n/a                            { value -1; }
            }
        }
        description
            "A type that accommodates a `yang:date-and-time` and an enumeration, 'n/a'. The typedef
             assumes that the start of the Unix epoch (1970/01/01 00:00:00.0) is a special value
             and is mapped the enumeration to show that this is currently no end time available.
             All other date values are treated as normal `yang:date-and-time`s.";
    }

}
