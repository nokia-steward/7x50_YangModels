submodule nokia-conf-router-l2tp {

    yang-version "1.1";

    belongs-to nokia-conf { prefix "conf"; }

    import nokia-sros-yang-extensions     { prefix "sros-ext"; }
    import nokia-types-l2tp               { prefix "types-l2tp"; }
    import nokia-types-ppp                { prefix "types-ppp"; }
    import nokia-types-services           { prefix "types-services"; }
    import nokia-types-sros               { prefix "types-sros"; }

    include nokia-conf-aaa;
    include nokia-conf-groups;
    include nokia-conf-isa;
    include nokia-conf-pxc;
    include nokia-conf-redundancy;

    sros-ext:sros-major-release "rel26";
    organization "Nokia";
    contact
        "Nokia SR OS Support
         Web: <http://www.nokia.com>";
    description
        "Nokia YANG Data model to configure l2tp on SR OS based routers.

         Copyright 2016 Nokia. All rights reserved. Reproduction of this document
         is authorized on the condition that the foregoing copyright notice is included.

         This nokia-conf-router-l2tp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping conf-router-l2tp {
        container l2tp {
            when "../router-name = 'Base'" {
                description "only allowed in the Base router";
            }
            description "Enter the l2tp context";

            leaf admin-state {
                type types-sros:admin-state;
                default "disable";
                description "Administrative state of L2TP";
            }

            leaf local-address {
                type types-sros:ipv4-unicast-address;
                description "Local address";
            }

            leaf receive-window-size {
                type types-l2tp:base-receive-window-size;
                description "L2TP receive window size";
            }

            leaf hello-interval {
                type types-l2tp:base-hello-interval;
                description "Hello interval";
            }

            leaf idle-timeout {
                type types-l2tp:base-idle-timeout;
                description "Idle timeout";
            }

            leaf destruct-timeout {
                type types-l2tp:base-destruct-timeout;
                description "Destruction timeout";
            }

            leaf max-retries-estab {
                type types-l2tp:base-max-retries;
                description "Maximum retries for established tunnels";
            }

            leaf max-retries-not-estab {
                type types-l2tp:base-max-retries;
                description "Maximum retries for unestablished tunnels";
            }

            leaf rtm-debounce-time {
                type types-l2tp:rtm-debounce-time;
                description "Debounce timer that declares L2TP action for route table management events";
            }

            leaf radius-accounting-policy {
                type leafref {
                    path "../../../aaa/radius/l2tp-accounting-policy/name";
                }
                description "RADIUS accounting policy";
            }

            leaf peer-address-change-policy {
                type types-l2tp:peer-address-change-policy-option;
                description "Reaction for L2TP response from a different address";
            }

            leaf local-name {
                type types-l2tp:host-name;
                description "Local host name";
            }

            leaf password {
                type types-sros:encrypted-leaf {
                    length "1..166";
                }
                description "L2TP password";
            }

            leaf challenge {
                type boolean;
                default "false";
                description "Use challenge-response authentication";
            }

            leaf avp-hiding {
                type types-l2tp:base-avp-hiding;
                description "Attribute of the Value Pair (AVP) hiding algorithm";
            }

            leaf session-limit {
                type types-l2tp:base-session-limit;
                description "L2TP session limit of this router";
            }

            leaf group-session-limit {
                type types-l2tp:base-session-limit;
                description "L2TP session limit for each group of this router";
            }

            leaf tunnel-session-limit {
                type types-l2tp:base-tunnel-session-limit;
                description "L2TP session limit for each tunnel of this router";
            }

            leaf session-assign-method {
                type types-l2tp:base-session-assign-method;
                description "Session assignment method";
            }

            leaf next-attempt {
                type enumeration {
                    enum same-preference-level          { value 0; }
                    enum next-preference-level          { value 1; }
                }
                default "next-preference-level";
                description "Tunnel that is selected when previous session setup failed";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container exclude-avps {
                description "Enter the exclude-avps context";

                leaf calling-number {
                    type boolean;
                    default "false";
                    description "Calling Number AVP to exclude";
                }

                leaf initial-rx-lcp-conf-req {
                    type boolean;
                    default "false";
                    description "Exclude the Initial Received LCP CONFREQ AVP";
                }

            } // container exclude-avps

            container ignore-avps {
                description "Enter the ignore-avps context";

                leaf sequencing-required {
                    type boolean;
                    default "false";
                    description "Ignore Sequencing Required AVP";
                }

            } // container ignore-avps

            container replace-result-code {
                description "Enter the replace-result-code context";

                leaf cdn-invalid-dst {
                    type boolean;
                    default "false";
                    description "Replace result code with general error code";
                }

                leaf cdn-permanent-no-facilities {
                    type boolean;
                    default "false";
                    description "Replace result code with general error";
                }

                leaf cdn-temporary-no-facilities {
                    type boolean;
                    default "false";
                    description "Replace result code with general error";
                }

            } // container replace-result-code

            container lac {
                description "Enter the lac context";

                leaf df-bit {
                    type boolean;
                    default "true";
                    description "Send all L2TP packets with DF bit set to 1";
                }

                leaf calling-number-format {
                    type types-sros:ascii-specification {
                        length "1..255";
                        pattern "([^%]+|%[Scrsl%])+" {
                            error-message "'calling-number-format' must use text with %S %c %r %s %l escapes only";
                        }
                    }
                    default "%S %s";
                    description "Calling Number AVP for L2TP control messages";
                }

                container fragmentation {
                    presence "Enable the fragmentation context";
                    description "Enable the fragmentation context";

                    leaf default-action {
                        type types-l2tp:lac-fragmentation-action;
                        default "deny";
                        description "Default action for L2TP sessions";
                    }

                    leaf fpe {
                        type leafref {
                            path "../../../../../fwd-path-ext/fpe/fpe-id";
                        }
                        mandatory true;
                        description "FPE that constructs the data endpoints";
                    }

                } // container fragmentation

                container cisco-nas-port {
                    description "Enter the cisco-nas-port context";

                    leaf ethernet {
                        type types-sros:binary-specification {
                            pattern "([01]|(\\*[0123456789]+)?[smpoi])+" {
                                error-message "'ethernet' must be 0/1 or *N(s|m|p|o|i) bit-spec";
                            }
                        }
                        description "L2TP Cisco NAS port AVP with binary patterns for Ethernet";
                    }

                } // container cisco-nas-port

            } // container lac

            container tunnel-selection-blacklist {
                description "Enter the tunnel-selection-blacklist context";

                leaf max-time {
                    type int32 {
                        range "1..60";
                    }
                    units "minutes";
                    default "5";
                    description "Time that a tunnel or peer can remain in the denylist";
                }

                leaf max-list-length {
                    type union {
                        type int32 {
                            range "1..65535";
                        }
                        type enumeration {
                            enum infinite                       { value -1; }
                        }
                    }
                    default "infinite";
                    description "Number of tunnels or peers in the denylist";
                }

                leaf timeout-action {
                    type enumeration {
                        enum remove-from-blacklist          { value 0; }
                        enum try-one-session                { value 1; }
                    }
                    default "remove-from-blacklist";
                    description "Action when a tunnel or peer exceeds time in denylist";
                }

                container add-tunnel-on {
                    description "Enter the add-tunnel-on context";

                    leaf address-change-timeout {
                        type boolean;
                        default "false";
                        description "Enable a timed-out tunnel to be forced to the denylist";
                    }

                    leaf cdn-err-code {
                        type boolean;
                        default "false";
                        description "Add to deny if CDN is received with code: General error";
                    }

                    leaf cdn-invalid-dst {
                        type boolean;
                        default "false";
                        description "Force tunnel to the denylist in case of Result Codes 6";
                    }

                    leaf cdn-permanent-no-facilities {
                        type boolean;
                        default "false";
                        description "Force tunnel to the denylist in case of Result Codes 5";
                    }

                    leaf cdn-temporary-no-facilities {
                        type boolean;
                        default "false";
                        description "Force tunnel to the denylist in case of Result Codes 4";
                    }

                    leaf stop-ccn-err-code {
                        type boolean;
                        default "false";
                        description "Add to denylist if received with general error code";
                    }

                    leaf stop-ccn-other {
                        type boolean;
                        default "false";
                        description "Add to denylist if StopCCN received with general error";
                    }

                    leaf tx-cdn-not-established-in-time {
                        type boolean;
                        default "false";
                        description "Add to denylist if CDN transmitted with result code";
                    }

                } // container add-tunnel-on

            } // container tunnel-selection-blacklist

            container failover {
                description "Enter the failover context";

                leaf recovery-method {
                    type types-l2tp:base-failover-recovery-method;
                    description "Recovery method of the sequence numbers after failover";
                }

                leaf recovery-time {
                    type types-l2tp:base-failover-recovery-time;
                    description "Time requested from the L2TP peer before assuming failover as failed";
                }

                leaf recovery-max-session-lifetime {
                    type uint32 {
                        range "2..4294967295";
                    }
                    units "centiseconds";
                    default "2";
                    description "Subset of sessions that this system attempts to synchronize in the Session State Synchronization phase";
                }

                list track-srrp {
                    key "id";
                    description "Enter the track-srrp list instance";

                    leaf id {
                        type leafref {
                            path "../../../../../redundancy/multi-chassis/peer/sync/track-srrp/id";
                        }
                        description "SRRP instance ID for multi-chassis redundancy failover";
                    }

                    leaf peer {
                        type leafref {
                            path "../../../../../redundancy/multi-chassis/peer/ip-address";
                        }
                        mandatory true;
                        description "Multi-chassis peer address";
                    }

                    leaf sync-tag {
                        type types-sros:named-item;
                        mandatory true;
                        description "Synchronization tag on the multi-chassis peer";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list track-srrp

            } // container failover

            container l2tpv3 {
                description "Enter the l2tpv3 context";

                leaf password {
                    type types-sros:encrypted-leaf {
                        length "1..166";
                    }
                    description "L2TPv3 password";
                }

                leaf cookie-length {
                    type types-l2tp:base-v3-cookie-length;
                    description "Cookie field length";
                }

                leaf digest-type {
                    type types-l2tp:base-v3-digest-type;
                    description "Hashing algorithm that calculates the message digest";
                }

                leaf nonce-length {
                    type types-l2tp:base-v3-nonce-length;
                    description "Length of the local L2TPv3 nonce (random number)";
                }

                leaf public-tcp-mss-adjust {
                    type types-l2tp:base-v3-tcp-mss-adjust;
                    description "TCP maximum segment size (MSS) on public network";
                }

                leaf private-tcp-mss-adjust {
                    type types-l2tp:base-v3-tcp-mss-adjust;
                    description "TCP maximum segment size (MSS) on private network";
                }

                container transport-type {
                    description "Enter the transport-type context";

                    leaf ip {
                        type boolean;
                        default "false";
                        description "Use IP as the transport type for the L2TPv3 tunnel";
                    }

                } // container transport-type

            } // container l2tpv3

            container ethernet-tunnel {
                description "Enter the ethernet-tunnel context";

                leaf reconnect-timeout {
                    type types-l2tp:base-v3-reconnect-timeout;
                    description "Timeout for a session setup retry";
                }

            } // container ethernet-tunnel

            list group {
                key "tunnel-group-name";
                description "Enter the group list instance";

                leaf tunnel-group-name {
                    type types-sros:named-item-64 {
                        length "1..63";
                    }
                    description "Tunnel group name";
                }

                leaf admin-state {
                    type types-sros:admin-state;
                    default "disable";
                    description "Administrative state of the L2TP tunnel group";
                }

                leaf description {
                    type types-sros:description;
                    description "Text description";
                }

                leaf protocol {
                    type types-l2tp:protocol-version;
                    sros-ext:immutable;
                    description "Protocol version";
                }

                leaf local-address {
                    type types-sros:ipv4-unicast-address;
                    description "Local address";
                }

                leaf receive-window-size {
                    type types-l2tp:child-receive-window-size;
                    description "L2TP receive window size";
                }

                leaf hello-interval {
                    type types-l2tp:child-hello-interval;
                    description "Hello interval";
                }

                leaf idle-timeout {
                    type types-l2tp:child-idle-timeout;
                    description "Idle timeout";
                }

                leaf destruct-timeout {
                    type types-l2tp:child-destruct-timeout;
                    description "Destruction timeout";
                }

                leaf max-retries-estab {
                    type types-l2tp:child-max-retries;
                    description "Maximum retries for established tunnels";
                }

                leaf max-retries-not-estab {
                    type types-l2tp:child-max-retries;
                    description "Maximum retries for unestablished tunnels";
                }

                leaf radius-accounting-policy {
                    type leafref {
                        path "../../../../aaa/radius/l2tp-accounting-policy/name";
                    }
                    description "RADIUS accounting policy";
                }

                leaf local-name {
                    type types-l2tp:host-name;
                    description "Local host name used to distinguish tunnels";
                }

                leaf password {
                    type types-sros:encrypted-leaf {
                        length "1..166";
                    }
                    description "Password between L2TP LAC and LNS";
                }

                leaf challenge {
                    type types-sros:bool-with-inherit;
                    description "Enable use of challenge-response authentication";
                }

                leaf avp-hiding {
                    type types-l2tp:child-avp-hiding;
                    description "The AVP hiding algorithm";
                }

                leaf session-limit {
                    type types-l2tp:child-session-limit;
                    description "Session limit";
                }

                leaf session-assign-method {
                    type types-l2tp:child-session-assign-method;
                    description "Session assignment method";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container failover {
                    when "../protocol = 'v2'" {
                        description "Protocol must be v2 to access this container";
                    }
                    description "Enter the failover context";

                    leaf recovery-method {
                        type types-l2tp:child-failover-recovery-method;
                        description "Recovery method of the sequence numbers after failover";
                    }

                    leaf recovery-time {
                        type types-l2tp:child-failover-recovery-time;
                        description "Time requested from the L2TP peer before assuming failover as failed";
                    }

                } // container failover

                container lac {
                    when "../protocol = 'v2'" {
                        description "Protocol must be v2 to access this container";
                    }
                    description "Enter the lac context";

                    leaf df-bit {
                        type types-sros:bool-with-inherit;
                        description "DF (do not fragment) bit in data traffic transmitted as LAC";
                    }

                } // container lac

                container l2tpv3 {
                    when "not(../protocol = 'v2')" {
                        description "Protocol must be v3 or v3draft to access this container";
                    }
                    description "Enter the l2tpv3 context";

                    leaf rem-router-id {
                        type types-sros:ipv4-address;
                        default "0.0.0.0";
                        description "Filter on remote router ID";
                    }

                    leaf password {
                        type types-sros:encrypted-leaf {
                            length "1..166";
                        }
                        description "L2TPv3 password";
                    }

                    leaf track-password-change {
                        type boolean;
                        default "false";
                        description "Enable tracking of password changes";
                    }

                    leaf cookie-length {
                        type types-l2tp:child-v3-cookie-length;
                        description "Cookie field length";
                    }

                    leaf digest-type {
                        type types-l2tp:child-v3-digest-type;
                        description "Hashing algorithm that calculates the message digest";
                    }

                    leaf nonce-length {
                        type types-l2tp:child-v3-nonce-length;
                        description "Length for the local L2TPv3 nonce (random number)";
                    }

                    leaf public-tcp-mss-adjust {
                        type types-l2tp:child-v3-tcp-mss-adjust;
                        description "TCP Maximum Segment Size (MSS) on public network";
                    }

                    leaf private-tcp-mss-adjust {
                        type types-l2tp:child-v3-tcp-mss-adjust;
                        description "TCP maximum segment size (MSS) on private network";
                    }

                    container pw-cap-list {
                        description "Enter the pw-cap-list context";

                        leaf ethernet {
                            type boolean;
                            sros-ext:auto-restart-to-modify;
                            default "false";
                            description "Advertise Ethernet pseudowire type";
                        }

                        leaf ethernet-vlan {
                            type boolean;
                            sros-ext:auto-restart-to-modify;
                            default "false";
                            description "Advertise Ethernet VLAN pseudowire type";
                        }

                    } // container pw-cap-list

                } // container l2tpv3

                container ethernet-tunnel {
                    when "not(../protocol = 'v2')" {
                        description "Protocol must be v3 or v3draft to access this container";
                    }
                    description "Enter the ethernet-tunnel context";

                    leaf reconnect-timeout {
                        type types-l2tp:child-v3-reconnect-timeout;
                        description "Timeout for a session setup retry at group level";
                    }

                } // container ethernet-tunnel

                container lns {
                    when "../protocol = 'v2'" {
                        description "Protocol must be v2 to access this container";
                    }
                    description "Enter the lns context";

                    leaf load-balance-method {
                        type types-l2tp:base-load-balance-method;
                        default "per-session";
                        description "New sessions for L2TP ISA MDA";
                    }

                    leaf lns-group {
                        type leafref {
                            path "../../../../../isa/lns-group/id";
                        }
                        description "ISA LNS group";
                    }

                    container ppp {
                        description "Enter the ppp context";

                        leaf authentication-policy {
                            type types-sros:named-item;
                            description "Authentication policy when a DHCP message is received";
                        }

                        leaf user-db {
                            type types-sros:named-item;
                            description "Local user database for PPP PAP and CHAP authentication";
                        }

                        leaf proxy-lcp {
                            type boolean;
                            default "false";
                            description "Proxy LCP AVPs that are received from LAC";
                        }

                        leaf lcp-ignore-magic-numbers {
                            type boolean;
                            default "false";
                            description "Check magic number in echo request and reply messages";
                        }

                        leaf lcp-force-ack-accm {
                            type boolean;
                            default "false";
                            description "Force acknowledgement of the LCP Asynchronous Control Character Map (ACCM) option";
                        }

                        leaf reject-disabled-ncp {
                            type boolean;
                            default "false";
                            description "Force LCP Protocol Reject for IPv6CP Configure Request";
                        }

                        leaf mtu {
                            type types-l2tp:base-ppp-mtu;
                            default "1500";
                            description "Maximum PPP MTU size";
                        }

                        leaf proxy-authentication {
                            type boolean;
                            default "false";
                            description "Use authentication AVPs that are received from LAC";
                        }

                        leaf authentication {
                            type types-l2tp:base-ppp-auth-protocol;
                            default "pref-chap";
                            description "PPP authentication protocol to negotiate";
                        }

                        leaf ipcp-subnet-negotiation {
                            type boolean;
                            default "false";
                            description "Allow IPCP subnet negotiation for PPPoE hosts";
                        }

                        container default-group-interface {
                            description "Enter the default-group-interface context";

                            leaf interface {
                                type types-sros:named-item;
                                description "Group interface";
                            }

                            leaf service-name {
                                type types-services:service-name;
                                description "Administrative service name";
                            }

                        } // container default-group-interface

                        container keepalive {
                            description "Enter the keepalive context";

                            leaf interval {
                                type types-l2tp:base-lcp-keepalive-interval;
                                default "30";
                                description "PPP keepalive interval";
                            }

                            leaf multiplier {
                                type types-l2tp:base-lcp-keepalive-multiplier;
                                default "3";
                                description "PPP keepalive multiplier";
                            }

                        } // container keepalive

                        container chap-challenge-length {
                            description "Enter the chap-challenge-length context";

                            leaf start {
                                type types-l2tp:base-chap-challenge-length;
                                default "32";
                                description "Lower bound of the PPP CHAP challenge length";
                            }

                            leaf end {
                                type types-l2tp:base-chap-challenge-length;
                                default "64";
                                description "Upper bound of the PPP CHAP challenge length";
                            }

                        } // container chap-challenge-length

                    } // container ppp

                    container mlppp {
                        description "Enter the mlppp context";

                        leaf admin-state {
                            type types-sros:admin-state;
                            default "disable";
                            description "Administrative state of MLPPP in the L2TP tunnel group";
                        }

                        leaf max-links {
                            type types-l2tp:base-mlppp-max-links;
                            default "1";
                            description "Maximum MLPPP links";
                        }

                        leaf interleave {
                            type boolean;
                            default "false";
                            description "Enable link fragmentation and interleaving";
                        }

                        leaf max-fragment-delay {
                            type types-l2tp:base-mlppp-max-frag-delay;
                            default "no-fragmentation";
                            description "Maximum fragment delay caused by transmission on a link";
                        }

                        leaf reassembly-timeout {
                            type types-l2tp:base-mlppp-reassembly-timeout;
                            default "1000";
                            description "Reassembly timeout";
                        }

                        leaf short-sequence-numbers {
                            type boolean;
                            default "false";
                            description "Request a peer to send short sequence numbers";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container endpoint {
                            description "Enter the endpoint context";

                            choice endpoint {
                                case ip {

                                    leaf ip {
                                        type types-ppp:mlppp-ip-endpoint;
                                        description "Endpoint ID as an IP address";
                                    }

                                }
                                case mac {

                                    leaf mac {
                                        type types-ppp:mlppp-mac-endpoint;
                                        description "Endpoint ID as a MAC address";
                                    }

                                }
                            }
                        } // container endpoint

                    } // container mlppp

                } // container lns

                list tunnel {
                    key "tunnel-name";
                    max-elements 31;
                    description "Enter the tunnel list instance";

                    leaf tunnel-name {
                        type types-sros:named-item {
                            length "1..32";
                        }
                        description "Tunnel name";
                    }

                    leaf admin-state {
                        type types-sros:admin-state;
                        default "disable";
                        description "Administrative state of the L2TP tunnel";
                    }

                    leaf description {
                        type types-sros:description;
                        description "Text description";
                    }

                    leaf preference {
                        type uint32 {
                            range "0..16777215";
                        }
                        default "50";
                        description "Tunnel preference number with its group";
                    }

                    leaf auto-establish {
                        type boolean;
                        default "false";
                        description "Allow the tunnel to be automatically set up by the system";
                    }

                    leaf peer {
                        type types-sros:ipv4-unicast-address;
                        description "Peer address";
                    }

                    leaf local-address {
                        type types-sros:ipv4-unicast-address;
                        description "Local address";
                    }

                    leaf receive-window-size {
                        type types-l2tp:child-receive-window-size;
                        description "L2TP receive window size";
                    }

                    leaf hello-interval {
                        type types-l2tp:child-hello-interval;
                        description "Hello interval";
                    }

                    leaf idle-timeout {
                        type types-l2tp:child-idle-timeout;
                        description "Idle timeout";
                    }

                    leaf destruct-timeout {
                        type types-l2tp:child-destruct-timeout;
                        description "Destruction timeout";
                    }

                    leaf max-retries-estab {
                        type types-l2tp:child-max-retries;
                        description "Maximum retries for established tunnels";
                    }

                    leaf max-retries-not-estab {
                        type types-l2tp:child-max-retries;
                        description "Maximum retries for unestablished tunnels";
                    }

                    leaf radius-accounting-policy {
                        type leafref {
                            path "../../../../../aaa/radius/l2tp-accounting-policy/name";
                        }
                        description "RADIUS accounting policy";
                    }

                    leaf remote-name {
                        type types-l2tp:host-name;
                        description "Remote tunnel host name";
                    }

                    leaf local-name {
                        type types-l2tp:host-name;
                        description "Local host name used to distinguish tunnels";
                    }

                    leaf password {
                        type types-sros:encrypted-leaf {
                            length "1..166";
                        }
                        description "Password between L2TP LAC and LNS";
                    }

                    leaf challenge {
                        type types-sros:bool-with-inherit;
                        description "Enable use of challenge-response authentication";
                    }

                    leaf avp-hiding {
                        type types-l2tp:child-avp-hiding;
                        description "The AVP hiding algorithm";
                    }

                    leaf session-limit {
                        type types-l2tp:child-tunnel-session-limit;
                        description "L2TP session limit for each tunnel of this router";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container failover {
                        when "../../protocol = 'v2'" {
                            description "Protocol must be v2 to access this container";
                        }
                        description "Enter the failover context";

                        leaf recovery-method {
                            type types-l2tp:child-failover-recovery-method;
                            description "Recovery method of the sequence numbers after failover";
                        }

                        leaf recovery-time {
                            type types-l2tp:child-failover-recovery-time;
                            description "Time requested from the L2TP peer before assuming failover as failed";
                        }

                    } // container failover

                    container lac {
                        when "../../protocol = 'v2'" {
                            description "Protocol must be v2 to access this container";
                        }
                        description "Enter the lac context";

                        leaf df-bit {
                            type types-sros:bool-with-inherit;
                            description "DF (do not fragment) bit in data traffic transmitted as LAC";
                        }

                    } // container lac

                    container l2tpv3 {
                        when "not(../../protocol = 'v2')" {
                            description "Protocol must be v3 or v3draft to access this container";
                        }
                        description "Enter the l2tpv3 context";

                        leaf public-tcp-mss-adjust {
                            type types-l2tp:child-v3-tcp-mss-adjust;
                            description "TCP maximum segment size (MSS) on public network";
                        }

                        leaf private-tcp-mss-adjust {
                            type types-l2tp:child-v3-tcp-mss-adjust;
                            description "TCP maximum segment size (MSS) on private network";
                        }

                    } // container l2tpv3

                    container lns {
                        when "../../protocol = 'v2'" {
                            description "Protocol must be v2 to access this container";
                        }
                        description "Enter the lns context";

                        leaf load-balance-method {
                            type types-l2tp:child-load-balance-method;
                            description "New sessions for L2TP ISA MDA";
                        }

                        leaf lns-group {
                            type leafref {
                                path "../../../../../../isa/lns-group/id";
                            }
                            description "ISA LNS group";
                        }

                        container ppp {
                            description "Enter the ppp context";

                            leaf authentication-policy {
                                type types-sros:named-item;
                                description "Authentication policy when a DHCP message is received";
                            }

                            leaf user-db {
                                type types-sros:named-item;
                                description "Local user database for PPP PAP and CHAP authentication";
                            }

                            leaf proxy-lcp {
                                type types-sros:bool-with-inherit;
                                description "Use the Proxy LCP AVPs that are received from the LAC";
                            }

                            leaf lcp-ignore-magic-numbers {
                                type types-sros:bool-with-inherit;
                                description "Magic-Number field in LCP Echo-Request and LCP Echo-Reply messages that are checked";
                            }

                            leaf lcp-force-ack-accm {
                                type types-sros:bool-with-inherit;
                                description "Forced acknowledgement of the LCP Asynchronous Control Character Map (ACCM) option";
                            }

                            leaf reject-disabled-ncp {
                                type types-sros:bool-with-inherit;
                                description "Force LCP Project Reject for IPv6CP Configure Request";
                            }

                            leaf mtu {
                                type types-l2tp:child-ppp-mtu;
                                description "Maximum PPP MTU size";
                            }

                            leaf proxy-authentication {
                                type types-sros:bool-with-inherit;
                                description "Authentication AVPs that are received from LAC";
                            }

                            leaf authentication {
                                type types-l2tp:child-ppp-auth-protocol;
                                description "PPP authentication protocol to negotiate";
                            }

                            leaf ipcp-subnet-negotiation {
                                type types-sros:bool-with-inherit;
                                description "Use of IPCP subnet negotiation for PPPoE hosts";
                            }

                            container default-group-interface {
                                description "Enter the default-group-interface context";

                                leaf interface {
                                    type types-sros:named-item;
                                    description "Group interface";
                                }

                                leaf service-name {
                                    type types-services:service-name;
                                    description "Administrative service name";
                                }

                            } // container default-group-interface

                            container keepalive {
                                description "Enter the keepalive context";

                                leaf interval {
                                    type types-l2tp:child-lcp-keepalive-interval;
                                    description "PPP keepalive interval";
                                }

                                leaf multiplier {
                                    type types-l2tp:child-lcp-keepalive-multiplier;
                                    description "PPP keepalive multiplier";
                                }

                            } // container keepalive

                            container chap-challenge-length {
                                description "Enter the chap-challenge-length context";

                                leaf start {
                                    type types-l2tp:child-chap-challenge-length;
                                    description "Lower bound of the PPP CHAP challenge length";
                                }

                                leaf end {
                                    type types-l2tp:child-chap-challenge-length;
                                    description "Upper bound of the PPP CHAP challenge length";
                                }

                            } // container chap-challenge-length

                        } // container ppp

                        container mlppp {
                            description "Enter the mlppp context";

                            leaf admin-state {
                                type types-sros:admin-state-with-inherit;
                                description "Administrative state of MLPPP in the L2TP tunnel";
                            }

                            leaf max-links {
                                type types-l2tp:child-mlppp-max-links;
                                description "Maximum MLPPP links";
                            }

                            leaf interleave {
                                type types-sros:bool-with-inherit;
                                description "Use of Link fragmentation and interleaving";
                            }

                            leaf max-fragment-delay {
                                type types-l2tp:child-mlppp-max-frag-delay;
                                description "Maximum fragment delay caused by transmission on a link";
                            }

                            leaf reassembly-timeout {
                                type types-l2tp:child-mlppp-reassembly-timeout;
                                description "Reassembly timeout";
                            }

                            leaf short-sequence-numbers {
                                type types-sros:bool-with-inherit;
                                description "Request a peer to send short sequence numbers";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container endpoint {
                                description "Enter the endpoint context";

                                choice endpoint {
                                    case ip {

                                        leaf ip {
                                            type types-ppp:mlppp-ip-endpoint;
                                            description "Endpoint ID as an IP address";
                                        }

                                    }
                                    case mac {

                                        leaf mac {
                                            type types-ppp:mlppp-mac-endpoint;
                                            description "Endpoint ID as a MAC address";
                                        }

                                    }
                                }
                            } // container endpoint

                        } // container mlppp

                    } // container lns

                } // list tunnel

            } // list group

        } // container l2tp

    } // grouping conf-router-l2tp

}
