submodule nokia-state-oam-pm {

    yang-version "1.1";

    belongs-to nokia-state { prefix "state"; }

    import ietf-yang-types                { prefix "yang"; }
    import nokia-sros-yang-extensions     { prefix "sros-ext"; }
    import nokia-types-oam                { prefix "types-oam"; }
    import nokia-types-sros               { prefix "types-sros"; }

    sros-ext:sros-major-release "rel26";
    organization "Nokia";
    contact
        "Nokia SR OS Support
         Web: <http://www.nokia.com>";
    description
        "Nokia YANG Data model with operational state for OAM-PM configuration on SR OS based routers.

         Copyright 2016 Nokia. All rights reserved. Reproduction of this document
         is authorized on the condition that the foregoing copyright notice is included.

         This nokia-state-oam-pm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping state-oam-pm {
        container oam-pm {
            description "Enter the oam-pm context";

            list session {
                key "session-name";
                description "Enter the session list instance";

                leaf session-name {
                    type types-sros:named-item;
                    description "OAM-PM session name";
                }

                choice test-family-choice {
                    mandatory true;
                    case ethernet-case {

                        container ethernet {
                            description "Enter the ethernet context";

                            container dmm {
                                description "Enter the dmm context";

                                leaf oper-state {
                                    type enumeration {
                                        enum up                             { value 1; }
                                        enum down                           { value 2; }
                                    }
                                    description "Operational state of the OAM-PM test";
                                }

                                leaf oper-test-id {
                                    type uint32;
                                    description "Test Identifier used in the transmitted OAM-PM PDU's Test ID field";
                                }

                                leaf detected-tx-error {
                                    type types-oam:oam-pm-session-test-detected-tx-error;
                                    description
                                        "Reason for the specified test's current inability (if any) to launch request frames.

                                         For example, 'eth-parent-admin-down(4)' could be returned for an SLM test
                                         if the MEP to be tested is associated with a SAP which is
                                         administratively down.

                                         Not all request frame transmit failures are detected by this mechanism.
                                         It is possible that 'none' will be returned when the test is unable
                                         to transmit frames.";
                                }

                                list delay-events {
                                    key "bin-metric direction";
                                    description "Enter the delay-events list instance";

                                    leaf bin-metric {
                                        type enumeration {
                                            enum fd {
                                                value 1;
                                                description "Frame Delay";
                                            }
                                            enum fdr {
                                                value 2;
                                                description "Frame Delay Range";
                                            }
                                            enum ifdv {
                                                value 3;
                                                description "Inter-Frame Delay Variation";
                                            }
                                        }
                                        description "Frame Delay, Frame Delay Range, Inter-Frame Delay Variation";
                                    }

                                    leaf direction {
                                        type types-oam:direction;
                                        description "MEF-35 traffic flow direction of an OAM-PM delay test";
                                    }

                                    leaf last-tca-time {
                                        type yang:date-and-time;
                                        description
                                            "Date and time at the start of the measurement interval which generated
                                             the most recent delay-based Raise or Clear TCA for the specified session,
                                             test-type, and direction";
                                    }

                                    leaf oper-state {
                                        type enumeration {
                                            enum pending                        { value 1; }
                                            enum active                         { value 2; }
                                            enum not-active                     { value 3; }
                                        }
                                        description
                                            "Operational state of the Threshold Crossing Alerts (TCAs) for the specified session,
                                             test-type, bin-type and direction.

                                             The code points are as follows.  The conditions are evaluated in the
                                             order shown.
                                             pending
                                                is returned if the threshold configuration for the
                                                specified indices changed during the current measurement interval.
                                             active
                                                is returned if the specified indices have a default clear threshold configured,
                                                and the current measurement interval has generated a Raise TCA.
                                                is returned if the specified indices have a non-default clear threshold
                                                configured, and the most recent TCA generated was a Raise.
                                             not-active
                                                is returned for all other conditions (e.g. thresholding is not
                                                configured for the specified indices).";
                                    }

                                } // list delay-events

                                container statistics {
                                    description "Enter the statistics context";

                                    list measurement-interval {
                                        key "duration";
                                        description "Enter the measurement-interval list instance";

                                        leaf duration {
                                            type types-oam:statistics-measurement-interval-duration;
                                            description "Duration of the measurement interval";
                                        }

                                        leaf newest-index {
                                            type uint32 {
                                                range "1..max";
                                            }
                                            description "Interval number of the newest interval for the specified session, test type, and measurement-interval type";
                                        }

                                        list number {
                                            key "mi-number";
                                            description "Enter the number list instance";

                                            leaf mi-number {
                                                type uint32 {
                                                    range "1..max";
                                                }
                                                description "Measurement interval number (the most recent interval is newest-index)";
                                            }

                                            leaf oper-state {
                                                type enumeration {
                                                    enum in-progress                    { value 1; }
                                                    enum completed                      { value 2; }
                                                }
                                                description "Operational state of the specified measurement interval data set";
                                            }

                                            leaf suspect {
                                                type boolean;
                                                description "Measurement interval data set contains suspect information";
                                            }

                                            leaf start-time {
                                                type yang:date-and-time;
                                                description "Start time of the specified measurement interval data set";
                                            }

                                            leaf elapsed-time {
                                                type uint32;
                                                units "seconds";
                                                description "Time elapsed since data collection started for the specified measurement interval data set";
                                            }

                                            leaf frames-sent {
                                                type uint32;
                                                description "Number of test frames sent for the specified measurement interval data set";
                                            }

                                            leaf frames-received {
                                                type uint32;
                                                description "Number of test frames received for the specified measurement interval data set";
                                            }

                                            list bin-type {
                                                key "bin-metric";
                                                description "Enter the bin-type list instance";

                                                leaf bin-metric {
                                                    type enumeration {
                                                        enum fd {
                                                            value 1;
                                                            description "Frame Delay";
                                                        }
                                                        enum fdr {
                                                            value 2;
                                                            description "Frame Delay Range";
                                                        }
                                                        enum ifdv {
                                                            value 3;
                                                            description "Inter-Frame Delay Variation";
                                                        }
                                                    }
                                                    description "Frame Delay, Frame Delay Range, Inter-Frame Delay Variation";
                                                }

                                                container forward {
                                                    description "Enter the forward context";

                                                    leaf minimum {
                                                        type uint32;
                                                        units "microseconds";
                                                        description "Minimum delay for the specified session, test type, measurement interval type, interval number, bin type, and direction";
                                                    }

                                                    leaf maximum {
                                                        type uint32;
                                                        units "microseconds";
                                                        description "Maximum delay for the specified session, test type, measurement interval type, interval number, bin type, and direction";
                                                    }

                                                    leaf average {
                                                        type uint32;
                                                        units "microseconds";
                                                        description "Average delay for the specified session, test type, measurement interval type, interval number, bin type, and direction";
                                                    }

                                                } // container forward

                                                container backward {
                                                    description "Enter the backward context";

                                                    leaf minimum {
                                                        type uint32;
                                                        units "microseconds";
                                                        description "Minimum delay for the specified session, test type, measurement interval type, interval number, bin type, and direction";
                                                    }

                                                    leaf maximum {
                                                        type uint32;
                                                        units "microseconds";
                                                        description "Maximum delay for the specified session, test type, measurement interval type, interval number, bin type, and direction";
                                                    }

                                                    leaf average {
                                                        type uint32;
                                                        units "microseconds";
                                                        description "Average delay for the specified session, test type, measurement interval type, interval number, bin type, and direction";
                                                    }

                                                } // container backward

                                                container round-trip {
                                                    description "Enter the round-trip context";

                                                    leaf minimum {
                                                        type uint32;
                                                        units "microseconds";
                                                        description "Minimum delay for the specified session, test type, measurement interval type, interval number, bin type, and direction";
                                                    }

                                                    leaf maximum {
                                                        type uint32;
                                                        units "microseconds";
                                                        description "Maximum delay for the specified session, test type, measurement interval type, interval number, bin type, and direction";
                                                    }

                                                    leaf average {
                                                        type uint32;
                                                        units "microseconds";
                                                        description "Average delay for the specified session, test type, measurement interval type, interval number, bin type, and direction";
                                                    }

                                                } // container round-trip

                                                list bin {
                                                    key "bin-number";
                                                    description "Enter the bin list instance";

                                                    leaf bin-number {
                                                        type uint32 {
                                                            range "0..9";
                                                        }
                                                        description "Number of the bin";
                                                    }

                                                    leaf forward-measurements {
                                                        type uint32;
                                                        description "Number of frame delay measurements in the forward direction that fall within the configured range of the specified bin";
                                                    }

                                                    leaf backward-measurements {
                                                        type uint32;
                                                        description "Number of frame delay measurements in the backward direction that fall within the configured range of the specified bin";
                                                    }

                                                    leaf round-trip-measurements {
                                                        type uint32;
                                                        description "Number of round trip frame delay measurements that fall within the configured range of the specified bin";
                                                    }

                                                } // list bin

                                            } // list bin-type

                                        } // list number

                                    } // list measurement-interval

                                    container streaming {
                                        description "Enter the streaming context";

                                        list metric {
                                            key "metric-id";
                                            description "Enter the metric list instance";

                                            leaf metric-id {
                                                type enumeration {
                                                    enum fd-average                     { value 1; }
                                                    enum ifdv-average                   { value 2; }
                                                }
                                                description "OAM-PM streaming metric to be displayed";
                                            }

                                            list newest-closed {
                                                key "direction";
                                                description "Enter the newest-closed list instance";

                                                leaf direction {
                                                    type types-oam:direction;
                                                    description "MEF-35 traffic flow direction of an OAM-PM delay test";
                                                }

                                                leaf close-time {
                                                    type yang:date-and-time;
                                                    description "Timestamp taken when the streaming sample window closed";
                                                }

                                                leaf sample-count {
                                                    type uint32;
                                                    description "Number of successful measurements used to compute the statistics in the streaming sample window";
                                                }

                                                leaf suspect {
                                                    type boolean;
                                                    description "Streaming sample window contains suspect information";
                                                }

                                                leaf delay {
                                                    type uint32;
                                                    units "microseconds";
                                                    description "Delay statistic for the streaming sample window";
                                                }

                                            } // list newest-closed

                                        } // list metric

                                    } // container streaming

                                } // container statistics

                            } // container dmm

                            container lmm {
                                description "Enter the lmm context";

                                leaf oper-state {
                                    type enumeration {
                                        enum up                             { value 1; }
                                        enum down                           { value 2; }
                                    }
                                    description "Operational state of the OAM-PM test";
                                }

                                leaf oper-test-id {
                                    type uint32;
                                    description "Test Identifier used in the transmitted OAM-PM PDU's Test ID field";
                                }

                                leaf detected-tx-error {
                                    type types-oam:oam-pm-session-test-detected-tx-error;
                                    description
                                        "Reason for the specified test's current inability (if any) to launch request frames.

                                         For example, 'eth-parent-admin-down(4)' could be returned for an SLM test
                                         if the MEP to be tested is associated with a SAP which is
                                         administratively down.

                                         Not all request frame transmit failures are detected by this mechanism.
                                         It is possible that 'none' will be returned when the test is unable
                                         to transmit frames.";
                                }

                                container loss-events {
                                    description "Enter the loss-events context";

                                    list avg-flr-event {
                                        key "direction";
                                        description "Enter the avg-flr-event list instance";

                                        leaf direction {
                                            type enumeration {
                                                enum forward                        { value 1; }
                                                enum backward                       { value 2; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list avg-flr-event

                                    list chli-event {
                                        key "direction";
                                        description "Enter the chli-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list chli-event

                                    list hli-event {
                                        key "direction";
                                        description "Enter the hli-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list hli-event

                                    list unavailability-event {
                                        key "direction";
                                        description "Enter the unavailability-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list unavailability-event

                                    list undet-availability-event {
                                        key "direction";
                                        description "Enter the undet-availability-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list undet-availability-event

                                    list undet-unavailability-event {
                                        key "direction";
                                        description "Enter the undet-unavailability-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list undet-unavailability-event

                                } // container loss-events

                                container statistics {
                                    description "Enter the statistics context";

                                    list measurement-interval {
                                        key "duration";
                                        description "Enter the measurement-interval list instance";

                                        leaf duration {
                                            type types-oam:statistics-measurement-interval-duration;
                                            description "Duration of the measurement interval";
                                        }

                                        leaf newest-index {
                                            type uint32 {
                                                range "1..max";
                                            }
                                            description "Interval number of the newest interval for the specified session, test type, and measurement-interval type";
                                        }

                                        list number {
                                            key "mi-number";
                                            description "Enter the number list instance";

                                            leaf mi-number {
                                                type uint32 {
                                                    range "1..max";
                                                }
                                                description "Measurement interval number (the most recent interval is newest-index)";
                                            }

                                            leaf oper-state {
                                                type enumeration {
                                                    enum in-progress                    { value 1; }
                                                    enum completed                      { value 2; }
                                                }
                                                description "Operational state of the specified measurement interval data set";
                                            }

                                            leaf suspect {
                                                type boolean;
                                                description "Measurement interval data set contains suspect information";
                                            }

                                            leaf start-time {
                                                type yang:date-and-time;
                                                description "Start time of the specified measurement interval data set";
                                            }

                                            leaf elapsed-time {
                                                type uint32;
                                                units "seconds";
                                                description "Time elapsed since data collection started for the specified measurement interval data set";
                                            }

                                            leaf frames-sent {
                                                type uint32;
                                                description "Number of test frames sent for the specified measurement interval data set";
                                            }

                                            leaf frames-received {
                                                type uint32;
                                                description "Number of test frames received for the specified measurement interval data set";
                                            }

                                            container forward {
                                                description "Enter the forward context";

                                                leaf tx {
                                                    type uint64;
                                                    description "Number of test request frames transmitted for the specified direction and measurement interval data set";
                                                }

                                                leaf rx {
                                                    type uint64;
                                                    description "Number of test request frames received for the specified direction and measurement interval data set";
                                                }

                                                leaf available {
                                                    type uint32;
                                                    description "Number of availability indicators evaluated as Available for the specified direction and measurement interval data set";
                                                }

                                                leaf unavailable {
                                                    type uint32;
                                                    description "Number of availability indicators evaluated as Unavailable for the specified direction and measurement interval data set";
                                                }

                                                leaf undetermined-available {
                                                    type uint32;
                                                    description "Number of availability indicators evaluated as Available in a given direction, based on extrapolation from the previous state";
                                                }

                                                leaf undetermined-unavailable {
                                                    type uint32;
                                                    description "Number of availability indicators evaluated as Unavailable in a given direction, based on extrapolation from the previous state";
                                                }

                                                leaf high-loss-intervals {
                                                    type uint32;
                                                    description "Number of High Loss Intervals (HLIs) for the specified direction and measurement interval data set";
                                                }

                                                leaf consecutive-high-loss-intervals {
                                                    type uint32;
                                                    description "Number of Consecutive High Loss Intervals (CHLIs) for the specified direction and measurement interval data set";
                                                }

                                                leaf minimum-frame-loss-ratio {
                                                    type uint32;
                                                    units "millipercent";
                                                    description "Minimum Frame Loss Ratio (FLR) for the specified direction and measurement interval data set";
                                                }

                                                leaf maximum-frame-loss-ratio {
                                                    type uint32;
                                                    units "millipercent";
                                                    description "Maximum Frame Loss Ratio (FLR) for the specified direction and measurement interval data set";
                                                }

                                                leaf average-frame-loss-ratio {
                                                    type uint32;
                                                    units "millipercent";
                                                    description "Average Frame Loss Ratio (FLR) for the specified direction and measurement interval data set";
                                                }

                                                leaf undetermined-delta-ts {
                                                    type uint32;
                                                    description "Number of undetermined MEF-35 'delta_t's for the specified direction and measurement interval data set";
                                                }

                                            } // container forward

                                            container backward {
                                                description "Enter the backward context";

                                                leaf tx {
                                                    type uint64;
                                                    description "Number of test request frames transmitted for the specified direction and measurement interval data set";
                                                }

                                                leaf rx {
                                                    type uint64;
                                                    description "Number of test request frames received for the specified direction and measurement interval data set";
                                                }

                                                leaf available {
                                                    type uint32;
                                                    description "Number of availability indicators evaluated as Available for the specified direction and measurement interval data set";
                                                }

                                                leaf unavailable {
                                                    type uint32;
                                                    description "Number of availability indicators evaluated as Unavailable for the specified direction and measurement interval data set";
                                                }

                                                leaf undetermined-available {
                                                    type uint32;
                                                    description "Number of availability indicators evaluated as Available in a given direction, based on extrapolation from the previous state";
                                                }

                                                leaf undetermined-unavailable {
                                                    type uint32;
                                                    description "Number of availability indicators evaluated as Unavailable in a given direction, based on extrapolation from the previous state";
                                                }

                                                leaf high-loss-intervals {
                                                    type uint32;
                                                    description "Number of High Loss Intervals (HLIs) for the specified direction and measurement interval data set";
                                                }

                                                leaf consecutive-high-loss-intervals {
                                                    type uint32;
                                                    description "Number of Consecutive High Loss Intervals (CHLIs) for the specified direction and measurement interval data set";
                                                }

                                                leaf minimum-frame-loss-ratio {
                                                    type uint32;
                                                    units "millipercent";
                                                    description "Minimum Frame Loss Ratio (FLR) for the specified direction and measurement interval data set";
                                                }

                                                leaf maximum-frame-loss-ratio {
                                                    type uint32;
                                                    units "millipercent";
                                                    description "Maximum Frame Loss Ratio (FLR) for the specified direction and measurement interval data set";
                                                }

                                                leaf average-frame-loss-ratio {
                                                    type uint32;
                                                    units "millipercent";
                                                    description "Average Frame Loss Ratio (FLR) for the specified direction and measurement interval data set";
                                                }

                                                leaf undetermined-delta-ts {
                                                    type uint32;
                                                    description "Number of undetermined MEF-35 'delta_t's for the specified direction and measurement interval data set";
                                                }

                                            } // container backward

                                        } // list number

                                    } // list measurement-interval

                                } // container statistics

                            } // container lmm

                            container slm {
                                description "Enter the slm context";

                                leaf oper-state {
                                    type enumeration {
                                        enum up                             { value 1; }
                                        enum down                           { value 2; }
                                    }
                                    description "Operational state of the OAM-PM test";
                                }

                                leaf oper-test-id {
                                    type uint32;
                                    description "Test Identifier used in the transmitted OAM-PM PDU's Test ID field";
                                }

                                leaf detected-tx-error {
                                    type types-oam:oam-pm-session-test-detected-tx-error;
                                    description
                                        "Reason for the specified test's current inability (if any) to launch request frames.

                                         For example, 'eth-parent-admin-down(4)' could be returned for an SLM test
                                         if the MEP to be tested is associated with a SAP which is
                                         administratively down.

                                         Not all request frame transmit failures are detected by this mechanism.
                                         It is possible that 'none' will be returned when the test is unable
                                         to transmit frames.";
                                }

                                container loss-events {
                                    description "Enter the loss-events context";

                                    list avg-flr-event {
                                        key "direction";
                                        description "Enter the avg-flr-event list instance";

                                        leaf direction {
                                            type enumeration {
                                                enum forward                        { value 1; }
                                                enum backward                       { value 2; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list avg-flr-event

                                    list chli-event {
                                        key "direction";
                                        description "Enter the chli-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list chli-event

                                    list hli-event {
                                        key "direction";
                                        description "Enter the hli-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list hli-event

                                    list unavailability-event {
                                        key "direction";
                                        description "Enter the unavailability-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list unavailability-event

                                    list undet-availability-event {
                                        key "direction";
                                        description "Enter the undet-availability-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list undet-availability-event

                                    list undet-unavailability-event {
                                        key "direction";
                                        description "Enter the undet-unavailability-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list undet-unavailability-event

                                } // container loss-events

                                container statistics {
                                    description "Enter the statistics context";

                                    list measurement-interval {
                                        key "duration";
                                        description "Enter the measurement-interval list instance";

                                        leaf duration {
                                            type types-oam:statistics-measurement-interval-duration;
                                            description "Duration of the measurement interval";
                                        }

                                        leaf newest-index {
                                            type uint32 {
                                                range "1..max";
                                            }
                                            description "Interval number of the newest interval for the specified session, test type, and measurement-interval type";
                                        }

                                        list number {
                                            key "mi-number";
                                            description "Enter the number list instance";

                                            leaf mi-number {
                                                type uint32 {
                                                    range "1..max";
                                                }
                                                description "Measurement interval number (the most recent interval is newest-index)";
                                            }

                                            leaf oper-state {
                                                type enumeration {
                                                    enum in-progress                    { value 1; }
                                                    enum completed                      { value 2; }
                                                }
                                                description "Operational state of the specified measurement interval data set";
                                            }

                                            leaf suspect {
                                                type boolean;
                                                description "Measurement interval data set contains suspect information";
                                            }

                                            leaf start-time {
                                                type yang:date-and-time;
                                                description "Start time of the specified measurement interval data set";
                                            }

                                            leaf elapsed-time {
                                                type uint32;
                                                units "seconds";
                                                description "Time elapsed since data collection started for the specified measurement interval data set";
                                            }

                                            leaf frames-sent {
                                                type uint32;
                                                description "Number of test frames sent for the specified measurement interval data set";
                                            }

                                            leaf frames-received {
                                                type uint32;
                                                description "Number of test frames received for the specified measurement interval data set";
                                            }

                                            container forward {
                                                description "Enter the forward context";

                                                leaf tx {
                                                    type uint32;
                                                    description "Number of test request frames transmitted for the specified direction and measurement interval data set";
                                                }

                                                leaf rx {
                                                    type uint32;
                                                    description "Number of test request frames received for the specified direction and measurement interval data set";
                                                }

                                                leaf available {
                                                    type uint32;
                                                    description "Number of availability indicators evaluated as Available for the specified direction and measurement interval data set";
                                                }

                                                leaf unavailable {
                                                    type uint32;
                                                    description "Number of availability indicators evaluated as Unavailable for the specified direction and measurement interval data set";
                                                }

                                                leaf undetermined-available {
                                                    type uint32;
                                                    description "Number of availability indicators evaluated as Available in a given direction, based on extrapolation from the previous state";
                                                }

                                                leaf undetermined-unavailable {
                                                    type uint32;
                                                    description "Number of availability indicators evaluated as Unavailable in a given direction, based on extrapolation from the previous state";
                                                }

                                                leaf high-loss-intervals {
                                                    type uint32;
                                                    description "Number of High Loss Intervals (HLIs) for the specified direction and measurement interval data set";
                                                }

                                                leaf consecutive-high-loss-intervals {
                                                    type uint32;
                                                    description "Number of Consecutive High Loss Intervals (CHLIs) for the specified direction and measurement interval data set";
                                                }

                                                leaf minimum-frame-loss-ratio {
                                                    type uint32;
                                                    units "millipercent";
                                                    description "Minimum Frame Loss Ratio (FLR) for the specified direction and measurement interval data set";
                                                }

                                                leaf maximum-frame-loss-ratio {
                                                    type uint32;
                                                    units "millipercent";
                                                    description "Maximum Frame Loss Ratio (FLR) for the specified direction and measurement interval data set";
                                                }

                                                leaf average-frame-loss-ratio {
                                                    type uint32;
                                                    units "millipercent";
                                                    description "Average Frame Loss Ratio (FLR) for the specified direction and measurement interval data set";
                                                }

                                            } // container forward

                                            container backward {
                                                description "Enter the backward context";

                                                leaf tx {
                                                    type uint32;
                                                    description "Number of test request frames transmitted for the specified direction and measurement interval data set";
                                                }

                                                leaf rx {
                                                    type uint32;
                                                    description "Number of test request frames received for the specified direction and measurement interval data set";
                                                }

                                                leaf available {
                                                    type uint32;
                                                    description "Number of availability indicators evaluated as Available for the specified direction and measurement interval data set";
                                                }

                                                leaf unavailable {
                                                    type uint32;
                                                    description "Number of availability indicators evaluated as Unavailable for the specified direction and measurement interval data set";
                                                }

                                                leaf undetermined-available {
                                                    type uint32;
                                                    description "Number of availability indicators evaluated as Available in a given direction, based on extrapolation from the previous state";
                                                }

                                                leaf undetermined-unavailable {
                                                    type uint32;
                                                    description "Number of availability indicators evaluated as Unavailable in a given direction, based on extrapolation from the previous state";
                                                }

                                                leaf high-loss-intervals {
                                                    type uint32;
                                                    description "Number of High Loss Intervals (HLIs) for the specified direction and measurement interval data set";
                                                }

                                                leaf consecutive-high-loss-intervals {
                                                    type uint32;
                                                    description "Number of Consecutive High Loss Intervals (CHLIs) for the specified direction and measurement interval data set";
                                                }

                                                leaf minimum-frame-loss-ratio {
                                                    type uint32;
                                                    units "millipercent";
                                                    description "Minimum Frame Loss Ratio (FLR) for the specified direction and measurement interval data set";
                                                }

                                                leaf maximum-frame-loss-ratio {
                                                    type uint32;
                                                    units "millipercent";
                                                    description "Maximum Frame Loss Ratio (FLR) for the specified direction and measurement interval data set";
                                                }

                                                leaf average-frame-loss-ratio {
                                                    type uint32;
                                                    units "millipercent";
                                                    description "Average Frame Loss Ratio (FLR) for the specified direction and measurement interval data set";
                                                }

                                            } // container backward

                                        } // list number

                                    } // list measurement-interval

                                } // container statistics

                            } // container slm

                        } // container ethernet

                    }
                    case ip-case {

                        container ip {
                            description "Enter the ip context";

                            leaf in-use-source-udp-port {
                                type uint16;
                                description "Source UDP port used for the session's test";
                            }

                            container twamp-light {
                                description "Enter the twamp-light context";

                                leaf oper-state {
                                    type enumeration {
                                        enum up                             { value 1; }
                                        enum down                           { value 2; }
                                    }
                                    description "Operational state of the OAM-PM test";
                                }

                                leaf oper-test-id {
                                    type uint32;
                                    description "Test Identifier used in the transmitted OAM-PM PDU's Test ID field";
                                }

                                leaf detected-tx-error {
                                    type types-oam:oam-pm-session-test-detected-tx-error;
                                    description
                                        "Reason for the specified test's current inability (if any) to launch request frames.

                                         For example, 'eth-parent-admin-down(4)' could be returned for an SLM test
                                         if the MEP to be tested is associated with a SAP which is
                                         administratively down.

                                         Not all request frame transmit failures are detected by this mechanism.
                                         It is possible that 'none' will be returned when the test is unable
                                         to transmit frames.";
                                }

                                leaf liveness-oper-state {
                                    type types-oam:oam-pm-session-test-liveness-oper-state;
                                    description
                                        "Liveness operational state for the test, indicating whether or
                                         not the test is successfully sending and receiving test packets";
                                }

                                container stamp {
                                    description "Enter the stamp context";

                                    leaf session-sender-id {
                                        type uint32 {
                                            range "0|1..65535";
                                        }
                                        description "Session Sender ID allocated for the STAMP test";
                                    }

                                    leaf stamp-unrecognized-flags-received {
                                        type yang:counter32;
                                        description "Number of STAMP TLVs received from the reflector with the Unrecognized (U) bit set";
                                    }

                                    leaf stamp-malformed-flags-received {
                                        type yang:counter32;
                                        description "Number of STAMP TLVs received from the reflector with the Malformed (M) bit set";
                                    }

                                } // container stamp

                                list delay-events {
                                    key "bin-metric direction";
                                    description "Enter the delay-events list instance";

                                    leaf bin-metric {
                                        type enumeration {
                                            enum fd {
                                                value 1;
                                                description "Frame Delay";
                                            }
                                            enum fdr {
                                                value 2;
                                                description "Frame Delay Range";
                                            }
                                            enum ifdv {
                                                value 3;
                                                description "Inter-Frame Delay Variation";
                                            }
                                        }
                                        description "Frame Delay, Frame Delay Range, Inter-Frame Delay Variation";
                                    }

                                    leaf direction {
                                        type types-oam:direction;
                                        description "MEF-35 traffic flow direction of an OAM-PM delay test";
                                    }

                                    leaf last-tca-time {
                                        type yang:date-and-time;
                                        description
                                            "Date and time at the start of the measurement interval which generated
                                             the most recent delay-based Raise or Clear TCA for the specified session,
                                             test-type, and direction";
                                    }

                                    leaf oper-state {
                                        type enumeration {
                                            enum pending                        { value 1; }
                                            enum active                         { value 2; }
                                            enum not-active                     { value 3; }
                                        }
                                        description
                                            "Operational state of the Threshold Crossing Alerts (TCAs) for the specified session,
                                             test-type, bin-type and direction.

                                             The code points are as follows.  The conditions are evaluated in the
                                             order shown.
                                             pending
                                                is returned if the threshold configuration for the
                                                specified indices changed during the current measurement interval.
                                             active
                                                is returned if the specified indices have a default clear threshold configured,
                                                and the current measurement interval has generated a Raise TCA.
                                                is returned if the specified indices have a non-default clear threshold
                                                configured, and the most recent TCA generated was a Raise.
                                             not-active
                                                is returned for all other conditions (e.g. thresholding is not
                                                configured for the specified indices).";
                                    }

                                } // list delay-events

                                container loss-events {
                                    description "Enter the loss-events context";

                                    list avg-flr-event {
                                        key "direction";
                                        description "Enter the avg-flr-event list instance";

                                        leaf direction {
                                            type enumeration {
                                                enum forward                        { value 1; }
                                                enum backward                       { value 2; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list avg-flr-event

                                    list chli-event {
                                        key "direction";
                                        description "Enter the chli-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list chli-event

                                    list hli-event {
                                        key "direction";
                                        description "Enter the hli-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list hli-event

                                    list unavailability-event {
                                        key "direction";
                                        description "Enter the unavailability-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list unavailability-event

                                    list undet-availability-event {
                                        key "direction";
                                        description "Enter the undet-availability-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list undet-availability-event

                                    list undet-unavailability-event {
                                        key "direction";
                                        description "Enter the undet-unavailability-event list instance";

                                        leaf direction {
                                            type enumeration {
                                                enum forward                        { value 1; }
                                                enum backward                       { value 2; }
                                                enum aggregate                      { value 3; }
                                            }
                                            description "Traffic flow direction";
                                        }

                                        leaf last-tca-time {
                                            type yang:date-and-time;
                                            description
                                                "Date and time at the start of the measurement interval which generated
                                                 the most recent delay-based Raise or Clear TCA for the specified session,
                                                 test-type, and direction";
                                        }

                                        leaf oper-state {
                                            type enumeration {
                                                enum pending                        { value 1; }
                                                enum active                         { value 2; }
                                                enum not-active                     { value 3; }
                                            }
                                            description
                                                "Operational state of the Threshold Crossing Alerts (TCAs) for the specified session,
                                                 test-type, bin-type and direction.

                                                 The code points are as follows.  The conditions are evaluated in the
                                                 order shown.
                                                 pending
                                                    is returned if the threshold configuration for the
                                                    specified indices changed during the current measurement interval.
                                                 active
                                                    is returned if the specified indices have a default clear threshold configured,
                                                    and the current measurement interval has generated a Raise TCA.
                                                    is returned if the specified indices have a non-default clear threshold
                                                    configured, and the most recent TCA generated was a Raise.
                                                 not-active
                                                    is returned for all other conditions (e.g. thresholding is not
                                                    configured for the specified indices).";
                                        }

                                    } // list undet-unavailability-event

                                } // container loss-events

                                container statistics {
                                    description "Enter the statistics context";

                                    container delay {
                                        description "Enter the delay context";

                                        list measurement-interval {
                                            key "duration";
                                            description "Enter the measurement-interval list instance";

                                            leaf duration {
                                                type types-oam:statistics-measurement-interval-duration;
                                                description "Duration of the measurement interval";
                                            }

                                            leaf newest-index {
                                                type uint32 {
                                                    range "1..max";
                                                }
                                                description "Interval number of the newest interval for the specified session, test type, and measurement-interval type";
                                            }

                                            list number {
                                                key "mi-number";
                                                description "Enter the number list instance";

                                                leaf mi-number {
                                                    type uint32 {
                                                        range "1..max";
                                                    }
                                                    description "Measurement interval number (the most recent interval is newest-index)";
                                                }

                                                leaf oper-state {
                                                    type enumeration {
                                                        enum in-progress                    { value 1; }
                                                        enum completed                      { value 2; }
                                                    }
                                                    description "Operational state of the specified measurement interval data set";
                                                }

                                                leaf suspect {
                                                    type boolean;
                                                    description "Measurement interval data set contains suspect information";
                                                }

                                                leaf start-time {
                                                    type yang:date-and-time;
                                                    description "Start time of the specified measurement interval data set";
                                                }

                                                leaf elapsed-time {
                                                    type uint32;
                                                    units "seconds";
                                                    description "Time elapsed since data collection started for the specified measurement interval data set";
                                                }

                                                leaf frames-sent {
                                                    type uint32;
                                                    description "Number of test frames sent for the specified measurement interval data set";
                                                }

                                                leaf frames-received {
                                                    type uint32;
                                                    description "Number of test frames received for the specified measurement interval data set";
                                                }

                                                list bin-type {
                                                    key "bin-metric";
                                                    description "Enter the bin-type list instance";

                                                    leaf bin-metric {
                                                        type enumeration {
                                                            enum fd {
                                                                value 1;
                                                                description "Frame Delay";
                                                            }
                                                            enum fdr {
                                                                value 2;
                                                                description "Frame Delay Range";
                                                            }
                                                            enum ifdv {
                                                                value 3;
                                                                description "Inter-Frame Delay Variation";
                                                            }
                                                        }
                                                        description "Frame Delay, Frame Delay Range, Inter-Frame Delay Variation";
                                                    }

                                                    container forward {
                                                        description "Enter the forward context";

                                                        leaf minimum {
                                                            type uint32;
                                                            units "microseconds";
                                                            description "Minimum delay for the specified session, test type, measurement interval type, interval number, bin type, and direction";
                                                        }

                                                        leaf maximum {
                                                            type uint32;
                                                            units "microseconds";
                                                            description "Maximum delay for the specified session, test type, measurement interval type, interval number, bin type, and direction";
                                                        }

                                                        leaf average {
                                                            type uint32;
                                                            units "microseconds";
                                                            description "Average delay for the specified session, test type, measurement interval type, interval number, bin type, and direction";
                                                        }

                                                    } // container forward

                                                    container backward {
                                                        description "Enter the backward context";

                                                        leaf minimum {
                                                            type uint32;
                                                            units "microseconds";
                                                            description "Minimum delay for the specified session, test type, measurement interval type, interval number, bin type, and direction";
                                                        }

                                                        leaf maximum {
                                                            type uint32;
                                                            units "microseconds";
                                                            description "Maximum delay for the specified session, test type, measurement interval type, interval number, bin type, and direction";
                                                        }

                                                        leaf average {
                                                            type uint32;
                                                            units "microseconds";
                                                            description "Average delay for the specified session, test type, measurement interval type, interval number, bin type, and direction";
                                                        }

                                                    } // container backward

                                                    container round-trip {
                                                        description "Enter the round-trip context";

                                                        leaf minimum {
                                                            type uint32;
                                                            units "microseconds";
                                                            description "Minimum delay for the specified session, test type, measurement interval type, interval number, bin type, and direction";
                                                        }

                                                        leaf maximum {
                                                            type uint32;
                                                            units "microseconds";
                                                            description "Maximum delay for the specified session, test type, measurement interval type, interval number, bin type, and direction";
                                                        }

                                                        leaf average {
                                                            type uint32;
                                                            units "microseconds";
                                                            description "Average delay for the specified session, test type, measurement interval type, interval number, bin type, and direction";
                                                        }

                                                    } // container round-trip

                                                    list bin {
                                                        key "bin-number";
                                                        description "Enter the bin list instance";

                                                        leaf bin-number {
                                                            type uint32 {
                                                                range "0..9";
                                                            }
                                                            description "Number of the bin";
                                                        }

                                                        leaf forward-measurements {
                                                            type uint32;
                                                            description "Number of frame delay measurements in the forward direction that fall within the configured range of the specified bin";
                                                        }

                                                        leaf backward-measurements {
                                                            type uint32;
                                                            description "Number of frame delay measurements in the backward direction that fall within the configured range of the specified bin";
                                                        }

                                                        leaf round-trip-measurements {
                                                            type uint32;
                                                            description "Number of round trip frame delay measurements that fall within the configured range of the specified bin";
                                                        }

                                                    } // list bin

                                                } // list bin-type

                                            } // list number

                                        } // list measurement-interval

                                        container streaming {
                                            description "Enter the streaming context";

                                            list metric {
                                                key "metric-id";
                                                description "Enter the metric list instance";

                                                leaf metric-id {
                                                    type enumeration {
                                                        enum fd-average                     { value 1; }
                                                        enum ifdv-average                   { value 2; }
                                                    }
                                                    description "OAM-PM streaming metric to be displayed";
                                                }

                                                list newest-closed {
                                                    key "direction";
                                                    description "Enter the newest-closed list instance";

                                                    leaf direction {
                                                        type types-oam:direction;
                                                        description "MEF-35 traffic flow direction of an OAM-PM delay test";
                                                    }

                                                    leaf close-time {
                                                        type yang:date-and-time;
                                                        description "Timestamp taken when the streaming sample window closed";
                                                    }

                                                    leaf sample-count {
                                                        type uint32;
                                                        description "Number of successful measurements used to compute the statistics in the streaming sample window";
                                                    }

                                                    leaf suspect {
                                                        type boolean;
                                                        description "Streaming sample window contains suspect information";
                                                    }

                                                    leaf delay {
                                                        type uint32;
                                                        units "microseconds";
                                                        description "Delay statistic for the streaming sample window";
                                                    }

                                                } // list newest-closed

                                            } // list metric

                                        } // container streaming

                                    } // container delay

                                    container loss {
                                        description "Enter the loss context";

                                        list measurement-interval {
                                            key "duration";
                                            description "Enter the measurement-interval list instance";

                                            leaf duration {
                                                type types-oam:statistics-measurement-interval-duration;
                                                description "Duration of the measurement interval";
                                            }

                                            leaf newest-index {
                                                type uint32 {
                                                    range "1..max";
                                                }
                                                description "Interval number of the newest interval for the specified session, test type, and measurement-interval type";
                                            }

                                            list number {
                                                key "mi-number";
                                                description "Enter the number list instance";

                                                leaf mi-number {
                                                    type uint32 {
                                                        range "1..max";
                                                    }
                                                    description "Measurement interval number (the most recent interval is newest-index)";
                                                }

                                                leaf oper-state {
                                                    type enumeration {
                                                        enum in-progress                    { value 1; }
                                                        enum completed                      { value 2; }
                                                    }
                                                    description "Operational state of the specified measurement interval data set";
                                                }

                                                leaf suspect {
                                                    type boolean;
                                                    description "Measurement interval data set contains suspect information";
                                                }

                                                leaf start-time {
                                                    type yang:date-and-time;
                                                    description "Start time of the specified measurement interval data set";
                                                }

                                                leaf elapsed-time {
                                                    type uint32;
                                                    units "seconds";
                                                    description "Time elapsed since data collection started for the specified measurement interval data set";
                                                }

                                                leaf frames-sent {
                                                    type uint32;
                                                    description "Number of test frames sent for the specified measurement interval data set";
                                                }

                                                leaf frames-received {
                                                    type uint32;
                                                    description "Number of test frames received for the specified measurement interval data set";
                                                }

                                                container forward {
                                                    description "Enter the forward context";

                                                    leaf tx {
                                                        type uint32;
                                                        description "Number of test request frames transmitted for the specified direction and measurement interval data set";
                                                    }

                                                    leaf rx {
                                                        type uint32;
                                                        description "Number of test request frames received for the specified direction and measurement interval data set";
                                                    }

                                                    leaf available {
                                                        type uint32;
                                                        description "Number of availability indicators evaluated as Available for the specified direction and measurement interval data set";
                                                    }

                                                    leaf unavailable {
                                                        type uint32;
                                                        description "Number of availability indicators evaluated as Unavailable for the specified direction and measurement interval data set";
                                                    }

                                                    leaf undetermined-available {
                                                        type uint32;
                                                        description "Number of availability indicators evaluated as Available in a given direction, based on extrapolation from the previous state";
                                                    }

                                                    leaf undetermined-unavailable {
                                                        type uint32;
                                                        description "Number of availability indicators evaluated as Unavailable in a given direction, based on extrapolation from the previous state";
                                                    }

                                                    leaf high-loss-intervals {
                                                        type uint32;
                                                        description "Number of High Loss Intervals (HLIs) for the specified direction and measurement interval data set";
                                                    }

                                                    leaf consecutive-high-loss-intervals {
                                                        type uint32;
                                                        description "Number of Consecutive High Loss Intervals (CHLIs) for the specified direction and measurement interval data set";
                                                    }

                                                    leaf minimum-frame-loss-ratio {
                                                        type uint32;
                                                        units "millipercent";
                                                        description "Minimum Frame Loss Ratio (FLR) for the specified direction and measurement interval data set";
                                                    }

                                                    leaf maximum-frame-loss-ratio {
                                                        type uint32;
                                                        units "millipercent";
                                                        description "Maximum Frame Loss Ratio (FLR) for the specified direction and measurement interval data set";
                                                    }

                                                    leaf average-frame-loss-ratio {
                                                        type uint32;
                                                        units "millipercent";
                                                        description "Average Frame Loss Ratio (FLR) for the specified direction and measurement interval data set";
                                                    }

                                                } // container forward

                                                container backward {
                                                    description "Enter the backward context";

                                                    leaf tx {
                                                        type uint32;
                                                        description "Number of test request frames transmitted for the specified direction and measurement interval data set";
                                                    }

                                                    leaf rx {
                                                        type uint32;
                                                        description "Number of test request frames received for the specified direction and measurement interval data set";
                                                    }

                                                    leaf available {
                                                        type uint32;
                                                        description "Number of availability indicators evaluated as Available for the specified direction and measurement interval data set";
                                                    }

                                                    leaf unavailable {
                                                        type uint32;
                                                        description "Number of availability indicators evaluated as Unavailable for the specified direction and measurement interval data set";
                                                    }

                                                    leaf undetermined-available {
                                                        type uint32;
                                                        description "Number of availability indicators evaluated as Available in a given direction, based on extrapolation from the previous state";
                                                    }

                                                    leaf undetermined-unavailable {
                                                        type uint32;
                                                        description "Number of availability indicators evaluated as Unavailable in a given direction, based on extrapolation from the previous state";
                                                    }

                                                    leaf high-loss-intervals {
                                                        type uint32;
                                                        description "Number of High Loss Intervals (HLIs) for the specified direction and measurement interval data set";
                                                    }

                                                    leaf consecutive-high-loss-intervals {
                                                        type uint32;
                                                        description "Number of Consecutive High Loss Intervals (CHLIs) for the specified direction and measurement interval data set";
                                                    }

                                                    leaf minimum-frame-loss-ratio {
                                                        type uint32;
                                                        units "millipercent";
                                                        description "Minimum Frame Loss Ratio (FLR) for the specified direction and measurement interval data set";
                                                    }

                                                    leaf maximum-frame-loss-ratio {
                                                        type uint32;
                                                        units "millipercent";
                                                        description "Maximum Frame Loss Ratio (FLR) for the specified direction and measurement interval data set";
                                                    }

                                                    leaf average-frame-loss-ratio {
                                                        type uint32;
                                                        units "millipercent";
                                                        description "Average Frame Loss Ratio (FLR) for the specified direction and measurement interval data set";
                                                    }

                                                } // container backward

                                            } // list number

                                        } // list measurement-interval

                                    } // container loss

                                } // container statistics

                            } // container twamp-light

                        } // container ip

                    }
                    case mpls-case {

                        container mpls {
                            description "Enter the mpls context";

                            container dm {
                                description "Enter the dm context";

                                leaf oper-state {
                                    type enumeration {
                                        enum up                             { value 1; }
                                        enum down                           { value 2; }
                                    }
                                    description "Operational state of the OAM-PM test";
                                }

                                leaf oper-test-id {
                                    type uint32;
                                    description "Test Identifier used in the transmitted OAM-PM PDU's Test ID field";
                                }

                                leaf rx-status {
                                    type types-oam:oam-pm-session-mpls-dm-rx-status;
                                    description "Most recent status received in an MPLS-DM response for the specified MPLS-DM test";
                                }

                                leaf udp-return-object-port {
                                    type types-sros:tcp-udp-port;
                                    description "UDP port used to receive all out-of-band MPLS-DM responses";
                                }

                                leaf detected-tx-error {
                                    type types-oam:oam-pm-session-test-detected-tx-error;
                                    description
                                        "Reason for the specified test's current inability (if any) to launch request frames.

                                         For example, 'eth-parent-admin-down(4)' could be returned for an SLM test
                                         if the MEP to be tested is associated with a SAP which is
                                         administratively down.

                                         Not all request frame transmit failures are detected by this mechanism.
                                         It is possible that 'none' will be returned when the test is unable
                                         to transmit frames.";
                                }

                                list delay-events {
                                    key "bin-metric direction";
                                    description "Enter the delay-events list instance";

                                    leaf bin-metric {
                                        type enumeration {
                                            enum fd {
                                                value 1;
                                                description "Frame Delay";
                                            }
                                            enum fdr {
                                                value 2;
                                                description "Frame Delay Range";
                                            }
                                            enum ifdv {
                                                value 3;
                                                description "Inter-Frame Delay Variation";
                                            }
                                        }
                                        description "Frame Delay, Frame Delay Range, Inter-Frame Delay Variation";
                                    }

                                    leaf direction {
                                        type types-oam:direction;
                                        description "MEF-35 traffic flow direction of an OAM-PM delay test";
                                    }

                                    leaf last-tca-time {
                                        type yang:date-and-time;
                                        description
                                            "Date and time at the start of the measurement interval which generated
                                             the most recent delay-based Raise or Clear TCA for the specified session,
                                             test-type, and direction";
                                    }

                                    leaf oper-state {
                                        type enumeration {
                                            enum pending                        { value 1; }
                                            enum active                         { value 2; }
                                            enum not-active                     { value 3; }
                                        }
                                        description
                                            "Operational state of the Threshold Crossing Alerts (TCAs) for the specified session,
                                             test-type, bin-type and direction.

                                             The code points are as follows.  The conditions are evaluated in the
                                             order shown.
                                             pending
                                                is returned if the threshold configuration for the
                                                specified indices changed during the current measurement interval.
                                             active
                                                is returned if the specified indices have a default clear threshold configured,
                                                and the current measurement interval has generated a Raise TCA.
                                                is returned if the specified indices have a non-default clear threshold
                                                configured, and the most recent TCA generated was a Raise.
                                             not-active
                                                is returned for all other conditions (e.g. thresholding is not
                                                configured for the specified indices).";
                                    }

                                } // list delay-events

                                container statistics {
                                    description "Enter the statistics context";

                                    list measurement-interval {
                                        key "duration";
                                        description "Enter the measurement-interval list instance";

                                        leaf duration {
                                            type types-oam:statistics-measurement-interval-duration;
                                            description "Duration of the measurement interval";
                                        }

                                        leaf newest-index {
                                            type uint32 {
                                                range "1..max";
                                            }
                                            description "Interval number of the newest interval for the specified session, test type, and measurement-interval type";
                                        }

                                        list number {
                                            key "mi-number";
                                            description "Enter the number list instance";

                                            leaf mi-number {
                                                type uint32 {
                                                    range "1..max";
                                                }
                                                description "Measurement interval number (the most recent interval is newest-index)";
                                            }

                                            leaf oper-state {
                                                type enumeration {
                                                    enum in-progress                    { value 1; }
                                                    enum completed                      { value 2; }
                                                }
                                                description "Operational state of the specified measurement interval data set";
                                            }

                                            leaf suspect {
                                                type boolean;
                                                description "Measurement interval data set contains suspect information";
                                            }

                                            leaf start-time {
                                                type yang:date-and-time;
                                                description "Start time of the specified measurement interval data set";
                                            }

                                            leaf elapsed-time {
                                                type uint32;
                                                units "seconds";
                                                description "Time elapsed since data collection started for the specified measurement interval data set";
                                            }

                                            leaf frames-sent {
                                                type uint32;
                                                description "Number of test frames sent for the specified measurement interval data set";
                                            }

                                            leaf frames-received {
                                                type uint32;
                                                description "Number of test frames received for the specified measurement interval data set";
                                            }

                                            list bin-type {
                                                key "bin-metric";
                                                description "Enter the bin-type list instance";

                                                leaf bin-metric {
                                                    type enumeration {
                                                        enum fd {
                                                            value 1;
                                                            description "Frame Delay";
                                                        }
                                                        enum fdr {
                                                            value 2;
                                                            description "Frame Delay Range";
                                                        }
                                                        enum ifdv {
                                                            value 3;
                                                            description "Inter-Frame Delay Variation";
                                                        }
                                                    }
                                                    description "Frame Delay, Frame Delay Range, Inter-Frame Delay Variation";
                                                }

                                                container forward {
                                                    description "Enter the forward context";

                                                    leaf minimum {
                                                        type uint32;
                                                        units "microseconds";
                                                        description "Minimum delay for the specified session, test type, measurement interval type, interval number, bin type, and direction";
                                                    }

                                                    leaf maximum {
                                                        type uint32;
                                                        units "microseconds";
                                                        description "Maximum delay for the specified session, test type, measurement interval type, interval number, bin type, and direction";
                                                    }

                                                    leaf average {
                                                        type uint32;
                                                        units "microseconds";
                                                        description "Average delay for the specified session, test type, measurement interval type, interval number, bin type, and direction";
                                                    }

                                                } // container forward

                                                container backward {
                                                    description "Enter the backward context";

                                                    leaf minimum {
                                                        type uint32;
                                                        units "microseconds";
                                                        description "Minimum delay for the specified session, test type, measurement interval type, interval number, bin type, and direction";
                                                    }

                                                    leaf maximum {
                                                        type uint32;
                                                        units "microseconds";
                                                        description "Maximum delay for the specified session, test type, measurement interval type, interval number, bin type, and direction";
                                                    }

                                                    leaf average {
                                                        type uint32;
                                                        units "microseconds";
                                                        description "Average delay for the specified session, test type, measurement interval type, interval number, bin type, and direction";
                                                    }

                                                } // container backward

                                                container round-trip {
                                                    description "Enter the round-trip context";

                                                    leaf minimum {
                                                        type uint32;
                                                        units "microseconds";
                                                        description "Minimum delay for the specified session, test type, measurement interval type, interval number, bin type, and direction";
                                                    }

                                                    leaf maximum {
                                                        type uint32;
                                                        units "microseconds";
                                                        description "Maximum delay for the specified session, test type, measurement interval type, interval number, bin type, and direction";
                                                    }

                                                    leaf average {
                                                        type uint32;
                                                        units "microseconds";
                                                        description "Average delay for the specified session, test type, measurement interval type, interval number, bin type, and direction";
                                                    }

                                                } // container round-trip

                                                list bin {
                                                    key "bin-number";
                                                    description "Enter the bin list instance";

                                                    leaf bin-number {
                                                        type uint32 {
                                                            range "0..9";
                                                        }
                                                        description "Number of the bin";
                                                    }

                                                    leaf forward-measurements {
                                                        type uint32;
                                                        description "Number of frame delay measurements in the forward direction that fall within the configured range of the specified bin";
                                                    }

                                                    leaf backward-measurements {
                                                        type uint32;
                                                        description "Number of frame delay measurements in the backward direction that fall within the configured range of the specified bin";
                                                    }

                                                    leaf round-trip-measurements {
                                                        type uint32;
                                                        description "Number of round trip frame delay measurements that fall within the configured range of the specified bin";
                                                    }

                                                } // list bin

                                            } // list bin-type

                                        } // list number

                                    } // list measurement-interval

                                    container streaming {
                                        description "Enter the streaming context";

                                        list metric {
                                            key "metric-id";
                                            description "Enter the metric list instance";

                                            leaf metric-id {
                                                type enumeration {
                                                    enum fd-average                     { value 1; }
                                                    enum ifdv-average                   { value 2; }
                                                }
                                                description "OAM-PM streaming metric to be displayed";
                                            }

                                            list newest-closed {
                                                key "direction";
                                                description "Enter the newest-closed list instance";

                                                leaf direction {
                                                    type types-oam:direction;
                                                    description "MEF-35 traffic flow direction of an OAM-PM delay test";
                                                }

                                                leaf close-time {
                                                    type yang:date-and-time;
                                                    description "Timestamp taken when the streaming sample window closed";
                                                }

                                                leaf sample-count {
                                                    type uint32;
                                                    description "Number of successful measurements used to compute the statistics in the streaming sample window";
                                                }

                                                leaf suspect {
                                                    type boolean;
                                                    description "Streaming sample window contains suspect information";
                                                }

                                                leaf delay {
                                                    type uint32;
                                                    units "microseconds";
                                                    description "Delay statistic for the streaming sample window";
                                                }

                                            } // list newest-closed

                                        } // list metric

                                    } // container streaming

                                } // container statistics

                            } // container dm

                        } // container mpls

                    }
                }
            } // list session

        } // container oam-pm

    } // grouping state-oam-pm

}
