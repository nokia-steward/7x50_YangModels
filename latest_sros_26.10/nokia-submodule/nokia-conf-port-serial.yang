submodule nokia-conf-port-serial {

    yang-version "1.1";

    belongs-to nokia-conf { prefix "conf"; }

    import nokia-sros-yang-extensions     { prefix "sros-ext"; }
    import nokia-types-port               { prefix "types-port"; }
    import nokia-types-sros               { prefix "types-sros"; }

    include nokia-conf-groups;

    sros-ext:sros-major-release "rel26";
    organization "Nokia";
    contact
        "Nokia SR OS Support
         Web: <http://www.nokia.com>";
    description
        "Nokia YANG Data model to configure Serial ports on SR OS based routers.

         Copyright 2016 Nokia. All rights reserved. Reproduction of this document
         is authorized on the condition that the foregoing copyright notice is included.

         This nokia-conf-port-serial YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping conf-port-serial {
        container serial {
            description "Enter the serial context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container rs232 {
                presence "Enable the rs232 context";
                description "Enable the rs232 context";

                leaf admin-state {
                    type types-sros:admin-state;
                    default "disable";
                    description "Administratively enable/disable the RS-232 port.";
                }

                leaf character-length {
                    type uint32 {
                        range "6..8";
                    }
                    default "8";
                    description "Number of data bits used to transmit a character.";
                }

                leaf data-position {
                    type enumeration {
                        enum f0-b5                          { value 1; }
                        enum f0-b6                          { value 2; }
                        enum none                           { value 3; }
                    }
                    description "HCM data start position.";
                }

                leaf loopback {
                    type enumeration {
                        enum none                           { value 1; }
                        enum bidir-e                        { value 2; }
                    }
                    default "none";
                    description "Activate a loopback on the serial port.";
                }

                leaf parity {
                    type enumeration {
                        enum none                           { value 1; }
                        enum odd                            { value 2; }
                        enum even                           { value 3; }
                        enum mark                           { value 4; }
                        enum space                          { value 5; }
                    }
                    default "none";
                    description "The parity bit in a character.";
                }

                leaf s-bit-signaling {
                    type boolean;
                    description "S-bit signaling mode.";
                }

                leaf speed {
                    type uint32 {
                        range "600|1200|2400|4800|9600|19200|38400|57600|115200";
                    }
                    default "9600";
                    description "The speed of the serial interface.";
                }

                leaf stop-bits {
                    type uint32 {
                        range "1..2";
                    }
                    default "1";
                    description "Number of stop bits on the serial interface.";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container hold-time {
                    description "Enter the hold-time context";

                    leaf up {
                        type uint32 {
                            range "0..100";
                        }
                        units "deciseconds";
                        default "0";
                        description "Hold timer for link up event dampening.";
                    }

                    leaf down {
                        type uint32 {
                            range "0..100";
                        }
                        units "deciseconds";
                        default "0";
                        description "Hold timer for link down event dampening.";
                    }

                } // container hold-time

                container mon-data-inactivity {
                    description "Enter the mon-data-inactivity context";

                    leaf raise {
                        type uint32 {
                            range "10|20|30|40|50|60|70|80|90|100";
                        }
                        units "seconds";
                        description "Debounce timer for raising data inactivity monitoring.";
                    }

                    leaf clear {
                        type uint32 {
                            range "10|20|30|40|50|60|70|80|90|100";
                        }
                        units "seconds";
                        description "Debounce timer for clearing data inactivity monitoring.";
                    }

                } // container mon-data-inactivity

                container report-alarm {
                    description "Enter the report-alarm context";

                    leaf hcm-oof {
                        type boolean;
                        description "Enable/disable local HCM oof alarm.";
                    }

                    leaf hcm-rai {
                        type boolean;
                        description "Enable/disable remote HCM rai alarm.";
                    }

                    leaf ctrl-lead-mon {
                        type boolean;
                        description "Enable/disable control lead monitoring alarm.";
                    }

                    leaf mon-data-inact {
                        type boolean;
                        description "Enable/disable data inactivity monitoring alarm.";
                    }

                } // container report-alarm

                list channel-group {
                    key "ds0-index";
                    description "Enter the channel-group list instance";

                    leaf ds0-index {
                        type uint32 {
                            range "1";
                        }
                        description "Specifies the DS0 channel group.";
                    }

                    leaf admin-state {
                        type types-sros:admin-state;
                        default "disable";
                        description "Administratively enable/disable the RS232 channel group.";
                    }

                    leaf description {
                        type types-sros:long-description;
                        default "DS0GRP";
                        description "Add/remove a text description.";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list channel-group

                container control-lead {
                    description "Enter the control-lead context";

                    container input {
                        description "Enter the input context";

                        leaf dts-dsr {
                            type types-port:control-lead;
                            default "high";
                            description "Data Terminal Ready (DTR) or Data Set Ready (DSR) input control lead.";
                        }

                        leaf rts-dcd {
                            type types-port:control-lead-hcm;
                            default "high";
                            description "Request To Send (RTS) or Data Carrier Detect (DCD) input control lead.";
                        }

                    } // container input

                    container output {
                        description "Enter the output context";

                        leaf cts-alb {
                            type types-port:control-lead-hcm;
                            default "high";
                            description "Clear To Send (CTS) or Analog Loopback (ALB) output control lead.";
                        }

                        leaf dcd-rts {
                            type types-port:control-lead-hcm;
                            default "high";
                            description "Data Carrier Detect (DCD) or Request To Send (RTS) output control lead.";
                        }

                        leaf ri-rdl {
                            type types-port:control-lead;
                            default "high";
                            description "Ring Indicator (RI) or Remote Digital Loopback (RDL) output control lead.";
                        }

                    } // container output

                    container monitor {
                        description "Enter the monitor context";

                        leaf dts-dsr {
                            type types-port:control-lead-monitor;
                            default "off";
                            description "Data Terminal Ready (DTR) or Data Set Ready (DSR) input control lead monitoring.";
                        }

                        leaf rts-dcd {
                            type types-port:control-lead-monitor;
                            default "off";
                            description "Request To Send (RTS) or Data Carrier Detect (DCD) input control lead monitoring.";
                        }

                    } // container monitor

                } // container control-lead

                list socket {
                    key "socket-id";
                    description "Enter the socket list instance";

                    leaf socket-id {
                        type uint32 {
                            range "1";
                        }
                        description "The socket identifier.";
                    }

                    leaf admin-state {
                        type types-sros:admin-state;
                        default "disable";
                        description "Administratively enable/disable the RS-232 socket.";
                    }

                    leaf description {
                        type types-sros:long-description;
                        default "SOCKET";
                        description "Add/remove a text description.";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container rx {
                        description "Enter the rx context";

                        leaf squelch-delay {
                            type uint32 {
                                range "1..120";
                            }
                            units "seconds";
                            description "The delay before squelch is automatically applied.";
                        }

                        leaf unsquelch-delay {
                            type uint32 {
                                range "1..120";
                            }
                            units "seconds";
                            description "The delay before squelch is automatically cleared.";
                        }

                        container eop {
                            description "Enter the eop context";

                            leaf idle-timeout {
                                type uint32 {
                                    range "10..5000";
                                }
                                units "milliseconds";
                                default "50";
                                description "The maximum period of idle time before triggering EOP.";
                            }

                            leaf length {
                                type uint32 {
                                    range "1..1500";
                                }
                                units "bytes";
                                default "1500";
                                description "The maximum number of received bytes before triggering EOP.";
                            }

                            leaf special-char {
                                type string {
                                    length "3..4";
                                }
                                description "A special character value used to trigger EOP.";
                            }

                        } // container eop

                    } // container rx

                    container tx {
                        description "Enter the tx context";

                        leaf inter-session-delay {
                            type uint32 {
                                range "0..5000";
                            }
                            units "milliseconds";
                            default "10";
                            description "The delay between sessions.";
                        }

                    } // container tx

                } // list socket

            } // container rs232

        } // container serial

    } // grouping conf-port-serial

}
