submodule nokia-state-svc-ipipe {

    yang-version "1.1";

    belongs-to nokia-state { prefix "state"; }

    import ietf-yang-types                { prefix "yang"; }
    import nokia-sros-yang-extensions     { prefix "sros-ext"; }
    import nokia-types-card               { prefix "types-card"; }
    import nokia-types-qos                { prefix "types-qos"; }
    import nokia-types-services           { prefix "types-services"; }
    import nokia-types-sros               { prefix "types-sros"; }

    include nokia-state-eth-cfm;

    sros-ext:sros-major-release "rel26";
    organization "Nokia";
    contact
        "Nokia SR OS Support
         Web: <http://www.nokia.com>";
    description
        "Nokia YANG Data model with operational state for ipipe services on SR OS based routers.

         Copyright 2016 Nokia. All rights reserved. Reproduction of this document
         is authorized on the condition that the foregoing copyright notice is included.

         This nokia-state-svc-ipipe YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping state-svc-ipipe {
        list ipipe {
            key "service-name";
            description "Enter the ipipe list instance";

            leaf service-name {
                type types-services:service-name;
                description "Name of the service";
            }

            leaf oper-service-id {
                type types-services:service-id;
                description "Service identifier";
            }

            leaf oper-state {
                type types-sros:oper-state;
                description "Operational state.";
            }

            leaf sap-count {
                type int32;
                description "Number of SAPs";
            }

            leaf sdp-bind-count {
                type int32;
                description "Number of SDP binds";
            }

            leaf template-used {
                type string;
                description "Template used to create this service";
            }

            leaf creation-origin {
                type types-sros:creation-origin;
                description "Creation origin of the service";
            }

            list endpoint {
                key "name";
                description "Enter the endpoint list instance";

                leaf name {
                    type types-sros:named-item;
                    description "Name of the service endpoint";
                }

                leaf revert-time-count-down {
                    type types-services:revert-time;
                    units "seconds";
                    description
                        "The count down timer that is used before reverting back to the primary spoke-sdp
                         defined on this service endpoint, after having failed over to
                         a backup spoke-sdp.

                         This count down timer begins after primary Spoke SDP becomes
                         operational.";
                }

                leaf creation-origin {
                    type enumeration {
                        enum manual                         { value 0; }
                        enum bgp-vpws                       { value 1; }
                    }
                    description "The origin mechanism used to create this endpoint.";
                }

                container tx-active {
                    description "Enter the tx-active context";

                    leaf type {
                        type enumeration {
                            enum none                           { value 0; }
                            enum sap                            { value 1; }
                            enum sdp-bind                       { value 2; }
                            enum sdp-fec                        { value 3; }
                            enum evpn                           { value 4; }
                        }
                        description "The type of endpoint object that is current transmit active. ";
                    }

                    leaf object {
                        type string;
                        description "The object that is transmit active";
                    }

                    leaf change-count {
                        type uint32;
                        description "The number of times active transmit change has taken place.";
                    }

                    leaf up-time {
                        type uint32;
                        units "centiseconds";
                        description
                            "The active 'up' time of the endpoint object
                             that is current transmit active.";
                    }

                } // container tx-active

            } // list endpoint

            list sap {
                key "sap-id";
                description "Enter the sap list instance";

                leaf sap-id {
                    type types-sros:sap;
                    description "SAP identifier";
                }

                leaf oper-state {
                    type enumeration {
                        enum up                             { value 1; }
                        enum down                           { value 2; }
                    }
                    description "Operating state of this SAP";
                }

                leaf mirror-state {
                    type enumeration {
                        enum ingress                        { value 1; }
                        enum egress                         { value 2; }
                        enum ingress-and-egress             { value 3; }
                        enum disabled                       { value 4; }
                    }
                    description "Indicates whether traffic mirroring has been enabled on this SAP";
                }

                leaf oper-flags {
                    type types-services:l2-sap-oper-flags;
                    description "Conditions that affect the operating status of this SAP.";
                }

                leaf template-used {
                    type types-sros:named-item-or-empty;
                    description "Name of the sap-template used to create this sap.";
                }

                leaf oper-dist-cpu-prot-policy {
                    type types-sros:named-item-or-empty;
                    description "Operational Distributed CPU Protection Policy.";
                }

                leaf arp-mac-address {
                    type yang:mac-address;
                    description "MAC address of the local end host.";
                }

                leaf arp-mac-address-timeout {
                    type uint32 {
                        range "0..65535";
                    }
                    description "MAC address timeout of the local end host.";
                }

                leaf discovered-ce-ip-address {
                    type types-sros:ipv4-address;
                    description "Discovered IPv4 address of local end host of an IPIPE SAP.";
                }

                leaf using-broadcast-mac {
                    type boolean;
                    description "Using broadcast MAC address to forward traffic from the Ethernet Ipipe SAP.";
                }

                container statistics {
                    description "Enter the statistics context";

                    container authentication {
                        description "Enter the authentication context";

                        leaf discarded-packets {
                            type yang:counter32;
                            description
                                "The number of DHCP packets discarded
                                 as result of authentication.";
                        }

                        leaf success-packets {
                            type yang:counter32;
                            description "The number of DHCP packets successfully authenticated.";
                        }

                    } // container authentication

                } // container statistics

                container ingress {
                    description "Enter the ingress context";

                    container qos {
                        description "Enter the qos context";

                        container sap-ingress {
                            description "Enter the sap-ingress context";

                            container forwarding-engine {
                                description "Enter the forwarding-engine context";

                                container statistics {
                                    description "Enter the statistics context";

                                    leaf dropped-packets {
                                        type yang:counter64;
                                        description
                                            "The number of packets dropped by the
                                             ingress packet processor due to: SAP state,
                                             ingress MAC, IP or IPv6 filter, same segment
                                             discard, bad checksum, etc.";
                                    }

                                    leaf dropped-octets {
                                        type yang:counter64;
                                        description
                                            "The number of octets dropped by the
                                             ingress packet processor due to: SAP state,
                                             ingress MAC, IP or IPv6 filter, same segment
                                             discard, bad checksum, etc.";
                                    }

                                    leaf received-valid-packets {
                                        type yang:counter64;
                                        description
                                            "The value of received-valid indicates
                                             number of received valid packets, as determined by the SAP
                                             ingress QoS policy, offered by the packet processor to the traffic manager.";
                                    }

                                    leaf received-valid-octets {
                                        type yang:counter64;
                                        description
                                            "The value of received-valid indicates
                                             number of received valid octets, as determined by the SAP
                                             ingress QoS policy, offered by the packet processor to the traffic manager.";
                                    }

                                    leaf high-priority-offered-packets {
                                        type yang:counter64;
                                        description
                                            "The number of high priority packets,
                                             as determined by the SAP ingress QoS
                                             policy, offered by the packet processor to the
                                             traffic manager.";
                                    }

                                    leaf high-priority-offered-octets {
                                        type yang:counter64;
                                        description
                                            "The number of high priority octets,
                                             as determined by the SAP ingress QoS
                                             policy, offered by the packet processor to the
                                             traffic manager.";
                                    }

                                    leaf low-priority-offered-packets {
                                        type yang:counter64;
                                        description
                                            "The number of low priority packets,
                                             as determined by the SAP ingress QoS
                                             policy, offered by the packet processor to the
                                             traffic manager.";
                                    }

                                    leaf low-priority-offered-octets {
                                        type yang:counter64;
                                        description
                                            "The number of low priority octets,
                                             as determined by the SAP ingress QoS
                                             policy, offered by the packet processor to the
                                             traffic manager.";
                                    }

                                    leaf uncolor-offered-packets {
                                        type yang:counter64;
                                        description
                                            "The number of uncolored packets,
                                             as determined by the SAP ingress QoS
                                             policy, offered by the packet processor to the
                                             traffic manager.";
                                    }

                                    leaf uncolor-offered-octets {
                                        type yang:counter64;
                                        description
                                            "The number of uncolored octets,
                                             as determined by the SAP ingress QoS
                                             policy, offered by the packet processor to the
                                             traffic manager.";
                                    }

                                    leaf managed-offered-packets {
                                        type yang:counter64;
                                        description
                                            "The value of managed-offered indicates
                                             number of managed multicast packets, as determined by the SAP
                                             ingress QoS policy, offered by the packet processor to the traffic manager.";
                                    }

                                    leaf managed-offered-octets {
                                        type yang:counter64;
                                        description
                                            "The value of managed-offered indicates
                                             number of managed multicast octets, as determined by the SAP
                                             ingress QoS policy, offered by the packet processor to the traffic manager.";
                                    }

                                    leaf aggregate-offered-packets {
                                        type yang:counter64;
                                        description
                                            "The value of aggregate-offered indicates aggregate
                                             number of hi, lo priority and uncolour packets,
                                             as determined by the SAP ingress QoS policy,
                                             offered by the packet processor to the traffic manager.";
                                    }

                                    leaf aggregate-offered-octets {
                                        type yang:counter64;
                                        description
                                            "The value of managed-offered indicates aggregate
                                             number of hi, lo priority and uncolour octets,
                                             as determined by the SAP ingress QoS policy,
                                             offered by the packet processor to the traffic manager.";
                                    }

                                    leaf last-cleared-time {
                                        type yang:date-and-time;
                                        description "Time when the counters in this table were last cleared.";
                                    }

                                } // container statistics

                            } // container forwarding-engine

                            container traffic-manager {
                                description "Enter the traffic-manager context";

                                container statistics {
                                    description "Enter the statistics context";

                                    leaf cpm-packets {
                                        type yang:counter64;
                                        description
                                            "The value of cpm-packets indicates
                                             ingress traffic in terms of packets destined to CPM
                                             associated with this SAP.";
                                    }

                                    leaf cpm-octets {
                                        type yang:counter64;
                                        description
                                            "The value of cpm indicates
                                             ingress traffic in terms of bytes destined to CPM
                                             associated with this SAP.";
                                    }

                                    leaf high-priority-dropped-packets {
                                        type yang:counter64;
                                        description
                                            "The number of high priority packets,
                                             as determined by the SAP ingress QoS
                                             policy, dropped by the traffic manager due to:
                                             MBS exceeded, buffer pool limit
                                             exceeded, etc.";
                                    }

                                    leaf high-priority-dropped-octets {
                                        type yang:counter64;
                                        description
                                            "The number of high priority octets,
                                             as determined by the SAP ingress QoS
                                             policy, dropped by the traffic manager due to:
                                             MBS exceeded, buffer pool limit
                                             exceeded, etc.";
                                    }

                                    leaf low-priority-dropped-packets {
                                        type yang:counter64;
                                        description
                                            "The number of low priority packets,
                                             as determined by the SAP ingress QoS
                                             policy, dropped by the traffic manager due to:
                                             MBS exceeded, buffer pool limit
                                             exceeded, etc.";
                                    }

                                    leaf low-priority-dropped-octets {
                                        type yang:counter64;
                                        description
                                            "The number of low priority octets,
                                             as determined by the SAP ingress QoS
                                             policy, dropped by the traffic manager due to:
                                             MBS exceeded, buffer pool limit
                                             exceeded, etc.";
                                    }

                                    leaf in-profile-forwarded-packets {
                                        type yang:counter64;
                                        description
                                            "The number of in-profile packets
                                             (rate below CIR) forwarded by the
                                             ingress traffic manager.";
                                    }

                                    leaf in-profile-forwarded-octets {
                                        type yang:counter64;
                                        description
                                            "The number of in-profile octets
                                             (rate below CIR) forwarded by the
                                             ingress traffic manager.";
                                    }

                                    leaf out-profile-forwarded-packets {
                                        type yang:counter64;
                                        description
                                            "The number of out-of-profile packets
                                             (rate above CIR) forwarded by the
                                             ingress traffic manager.";
                                    }

                                    leaf out-profile-forwarded-octets {
                                        type yang:counter64;
                                        description
                                            "The number of out-of-profile octets
                                             (rate above CIR) forwarded by the
                                             ingress traffic manager.";
                                    }

                                    leaf aggregate-forwarded-packets {
                                        type yang:counter64;
                                        description
                                            "The aggregate number of in and out-of profile
                                              packets forwarded by the ingress traffic manager.";
                                    }

                                    leaf aggregate-forwarded-octets {
                                        type yang:counter64;
                                        description
                                            "The aggregate number of in and out-of-profile
                                             octets forwarded by the ingress traffic manager.";
                                    }

                                    leaf aggregate-dropped-packets {
                                        type yang:counter64;
                                        description
                                            "The aggregate number of in and out-of profile
                                             packets, dropped by the traffic manager due to:
                                             MBS exceeded, buffer pool limit
                                             exceeded, etc.";
                                    }

                                    leaf aggregate-dropped-octets {
                                        type yang:counter64;
                                        description
                                            "The aggregate number of in and out-of profile
                                             octets, dropped by the traffic manager due to:
                                             MBS exceeded, buffer pool limit
                                             exceeded, etc.";
                                    }

                                    leaf last-cleared-time {
                                        type yang:date-and-time;
                                        description "Time when the counters in this table were last cleared.";
                                    }

                                } // container statistics

                            } // container traffic-manager

                            list queue {
                                key "queue-id";
                                description "Enter the queue list instance";

                                leaf queue-id {
                                    type types-qos:ingress-queue-id;
                                    description "The unique identifier for the queue.";
                                }

                                container statistics {
                                    description "Enter the statistics context";

                                    choice stat-mode {
                                        case unicast-priority {

                                            container unicast-priority {
                                                description "Enter the unicast-priority context";

                                                leaf high-priority-offered-packets {
                                                    type yang:counter64;
                                                    description "The number of high-priority packets offered by packet processor to traffic manager.";
                                                }

                                                leaf high-priority-offered-octets {
                                                    type yang:counter64;
                                                    description "The number of high-priority octets offered by packet processor to traffic manager.";
                                                }

                                                leaf low-priority-offered-packets {
                                                    type yang:counter64;
                                                    description "The number of low-priority packets offered by packet processor to traffic manager.";
                                                }

                                                leaf low-priority-offered-octets {
                                                    type yang:counter64;
                                                    description "The number of low-priority octets offered by packet processor to traffic manager.";
                                                }

                                                leaf high-priority-dropped-packets {
                                                    type yang:counter64;
                                                    description "The number of high-priority packets dropped by packet processor to traffic manager.";
                                                }

                                                leaf high-priority-dropped-octets {
                                                    type yang:counter64;
                                                    description "The number of high-priority octets dropped by packet processor to traffic manager.";
                                                }

                                                leaf low-priority-dropped-packets {
                                                    type yang:counter64;
                                                    description "The number of low-priority packets dropped by packet processor to traffic manager.";
                                                }

                                                leaf low-priority-dropped-octets {
                                                    type yang:counter64;
                                                    description "The number of low-priority octets dropped by packet processor to traffic manager.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container unicast-priority

                                        }
                                        case unicast-profile {

                                            container unicast-profile {
                                                description "Enter the unicast-profile context";

                                                leaf color-in-offered-packets {
                                                    type yang:counter64;
                                                    description "The number of color-in packets offered to traffic manager.";
                                                }

                                                leaf color-in-offered-octets {
                                                    type yang:counter64;
                                                    description "The number of color-in octets offered to traffic manager.";
                                                }

                                                leaf color-out-offered-packets {
                                                    type yang:counter64;
                                                    description "The number of color-out packets offered to traffic manager.";
                                                }

                                                leaf color-out-offered-octets {
                                                    type yang:counter64;
                                                    description "The number of color-out octets offered to traffic manager.";
                                                }

                                                leaf color-offered-packets {
                                                    type yang:counter64;
                                                    description "The number of color packets offered to traffic manager.";
                                                }

                                                leaf color-offered-octets {
                                                    type yang:counter64;
                                                    description "The number of color octets offered to traffic manager.";
                                                }

                                                leaf uncolor-offered-packets {
                                                    type yang:counter64;
                                                    description "The number of uncolor packets offered to traffic manager.";
                                                }

                                                leaf uncolor-offered-octets {
                                                    type yang:counter64;
                                                    description "The number of uncolor octets offered to traffic manager.";
                                                }

                                                leaf color-out-dropped-packets {
                                                    type yang:counter64;
                                                    description "The number of color-out packets dropped.";
                                                }

                                                leaf color-out-dropped-octets {
                                                    type yang:counter64;
                                                    description "The number of color-out octets dropped.";
                                                }

                                                leaf color-in-uncolor-dropped-packets {
                                                    type yang:counter64;
                                                    description "The number of color-in/uncolor packets dropped.";
                                                }

                                                leaf color-in-uncolor-dropped-octets {
                                                    type yang:counter64;
                                                    description "The number of color-in/uncolor octets dropped.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container unicast-profile

                                        }
                                        case multipoint-priority {

                                            container multipoint-priority {
                                                description "Enter the multipoint-priority context";

                                                leaf high-priority-offered-packets {
                                                    type yang:counter64;
                                                    description "The number of high-priority packets offered by packet processor to traffic manager.";
                                                }

                                                leaf high-priority-offered-octets {
                                                    type yang:counter64;
                                                    description "The number of high-priority octets offered by packet processor to traffic manager.";
                                                }

                                                leaf low-priority-offered-packets {
                                                    type yang:counter64;
                                                    description "The number of low-priority packets offered by packet processor to traffic manager.";
                                                }

                                                leaf low-priority-offered-octets {
                                                    type yang:counter64;
                                                    description "The number of low-priority octets offered by packet processor to traffic manager.";
                                                }

                                                leaf combined-offered-packets {
                                                    type yang:counter64;
                                                    description "The number of combined high and low priority packets offered by packet processor to traffic manager.";
                                                }

                                                leaf combined-offered-octets {
                                                    type yang:counter64;
                                                    description "The number of combined high and low priority octets offered by packet processor to traffic manager.";
                                                }

                                                leaf managed-offered-packets {
                                                    type yang:counter64;
                                                    description "The number of managed packets offered by packet processor to traffic manager.";
                                                }

                                                leaf managed-offered-octets {
                                                    type yang:counter64;
                                                    description "The number of managed octets offered by packet processor to traffic manager.";
                                                }

                                                leaf high-priority-dropped-packets {
                                                    type yang:counter64;
                                                    description "The number of high-priority packets dropped by packet processor to traffic manager.";
                                                }

                                                leaf high-priority-dropped-octets {
                                                    type yang:counter64;
                                                    description "The number of high-priority octets dropped by packet processor to traffic manager.";
                                                }

                                                leaf low-priority-dropped-packets {
                                                    type yang:counter64;
                                                    description "The number of low-priority packets dropped by packet processor to traffic manager.";
                                                }

                                                leaf low-priority-dropped-octets {
                                                    type yang:counter64;
                                                    description "The number of low-priority octets dropped by packet processor to traffic manager.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container multipoint-priority

                                        }
                                        case multipoint-profile {

                                            container multipoint-profile {
                                                description "Enter the multipoint-profile context";

                                                leaf color-in-offered-packets {
                                                    type yang:counter64;
                                                    description "The number of color-in packets offered to traffic manager.";
                                                }

                                                leaf color-in-offered-octets {
                                                    type yang:counter64;
                                                    description "The number of color-in octets offered to traffic manager.";
                                                }

                                                leaf color-out-offered-packets {
                                                    type yang:counter64;
                                                    description "The number of color-out packets offered to traffic manager.";
                                                }

                                                leaf color-out-offered-octets {
                                                    type yang:counter64;
                                                    description "The number of color-out octets offered to traffic manager.";
                                                }

                                                leaf uncolor-offered-packets {
                                                    type yang:counter64;
                                                    description "The number of uncolor packets offered to traffic manager.";
                                                }

                                                leaf uncolor-offered-octets {
                                                    type yang:counter64;
                                                    description "The number of uncolor octets offered to traffic manager.";
                                                }

                                                leaf combined-offered-packets {
                                                    type yang:counter64;
                                                    description "The number of combined colored in, out and uncolored packets offered to traffic manager.";
                                                }

                                                leaf combined-offered-octets {
                                                    type yang:counter64;
                                                    description "The number of combined colored in, out and uncolored octets offered to traffic manager.";
                                                }

                                                leaf managed-offered-packets {
                                                    type yang:counter64;
                                                    description "The number of managed packets offered by packet processor to traffic manager.";
                                                }

                                                leaf managed-offered-octets {
                                                    type yang:counter64;
                                                    description "The number of managed octets offered by packet processor to traffic manager.";
                                                }

                                                leaf color-out-dropped-packets {
                                                    type yang:counter64;
                                                    description "The number of color-out packets dropped.";
                                                }

                                                leaf color-out-dropped-octets {
                                                    type yang:counter64;
                                                    description "The number of color-out octets dropped.";
                                                }

                                                leaf color-in-uncolor-dropped-packets {
                                                    type yang:counter64;
                                                    description "The number of color-in/uncolor packets dropped.";
                                                }

                                                leaf color-in-uncolor-dropped-octets {
                                                    type yang:counter64;
                                                    description "The number of color-in/uncolor octets dropped.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container multipoint-profile

                                        }
                                        case v4-v6 {

                                            container v4-v6 {
                                                description "Enter the v4-v6 context";

                                                leaf ipv4-offered-packets {
                                                    type yang:counter64;
                                                    description "The number of ipv4 packets offered by packet processor to traffic manager.";
                                                }

                                                leaf ipv4-offered-octets {
                                                    type yang:counter64;
                                                    description "The number of ipv4 octets offered by packet processor to traffic manager.";
                                                }

                                                leaf ipv6-offered-packets {
                                                    type yang:counter64;
                                                    description "The number of ipv6 packets offered by packet processor to traffic manager.";
                                                }

                                                leaf ipv6-offered-octets {
                                                    type yang:counter64;
                                                    description "The number of ipv6 octets offered by packet processor to traffic manager.";
                                                }

                                                leaf ipv4-dropped-packets {
                                                    type yang:counter64;
                                                    description "The number of ipv4 packets dropped by packet processor to traffic manager.";
                                                }

                                                leaf ipv4-dropped-octets {
                                                    type yang:counter64;
                                                    description "The number of ipv4 octets dropped by packet processor to traffic manager.";
                                                }

                                                leaf ipv6-dropped-packets {
                                                    type yang:counter64;
                                                    description "The number of ipv6 packets dropped by packet processor to traffic manager.";
                                                }

                                                leaf ipv6-dropped-octets {
                                                    type yang:counter64;
                                                    description "The number of ipv6 octets dropped by packet processor to traffic manager.";
                                                }

                                                leaf ipv4-forwarded-packets {
                                                    type yang:counter64;
                                                    description "The number of ipv4 packets forwarded.";
                                                }

                                                leaf ipv4-forwarded-octets {
                                                    type yang:counter64;
                                                    description "The number of ipv4 octets forwarded.";
                                                }

                                                leaf ipv6-forwarded-packets {
                                                    type yang:counter64;
                                                    description "The number of ipv6 packets forwarded.";
                                                }

                                                leaf ipv6-forwarded-octets {
                                                    type yang:counter64;
                                                    description "The number of ipv6 octets forwarded.";
                                                }

                                            } // container v4-v6

                                        }
                                    }
                                } // container statistics

                                container queue-depth {
                                    description "Enter the queue-depth context";

                                    leaf elapsed-time {
                                        type types-sros:time-interval;
                                        description "Indicated the elapsed time.";
                                    }

                                    leaf depth-0-to-10-percent {
                                        type decimal64 {
                                            fraction-digits 2;
                                        }
                                        description "Indicated the depth 0 to 10 percent.";
                                    }

                                    leaf depth-11-to-20-percent {
                                        type decimal64 {
                                            fraction-digits 2;
                                        }
                                        description "Indicated the depth 0 to 20 percent.";
                                    }

                                    leaf depth-21-to-30-percent {
                                        type decimal64 {
                                            fraction-digits 2;
                                        }
                                        description "Indicated the depth 0 to 30 percent.";
                                    }

                                    leaf depth-31-to-40-percent {
                                        type decimal64 {
                                            fraction-digits 2;
                                        }
                                        description "Indicated the depth 0 to 40 percent.";
                                    }

                                    leaf depth-41-to-50-percent {
                                        type decimal64 {
                                            fraction-digits 2;
                                        }
                                        description "Indicated the depth 0 to 50 percent.";
                                    }

                                    leaf depth-51-to-60-percent {
                                        type decimal64 {
                                            fraction-digits 2;
                                        }
                                        description "Indicated the depth 0 to 60 percent.";
                                    }

                                    leaf depth-61-to-70-percent {
                                        type decimal64 {
                                            fraction-digits 2;
                                        }
                                        description "Indicated the depth 0 to 70 percent.";
                                    }

                                    leaf depth-71-to-80-percent {
                                        type decimal64 {
                                            fraction-digits 2;
                                        }
                                        description "Indicated the depth 0 to 80 percent.";
                                    }

                                    leaf depth-81-to-90-percent {
                                        type decimal64 {
                                            fraction-digits 2;
                                        }
                                        description "Indicated the depth 0 to 90 percent.";
                                    }

                                    leaf depth-91-to-100-percent {
                                        type decimal64 {
                                            fraction-digits 2;
                                        }
                                        description "Indicated the depth 0 to 100 percent.";
                                    }

                                    leaf queue-polling-interval {
                                        type types-sros:time-interval;
                                        description "Indicates the queue polling interval.";
                                    }

                                } // container queue-depth

                                list hardware-queue {
                                    key "source-card source-fp source-tap-offset source-port dest-card dest-fp dest-tap-offset";
                                    description "Enter the hardware-queue list instance";

                                    leaf source-card {
                                        type int32;
                                        description "Card number";
                                    }

                                    leaf source-fp {
                                        type int32;
                                        description "FP number";
                                    }

                                    leaf source-tap-offset {
                                        type int32;
                                        description "Source TAP.";
                                    }

                                    leaf source-port {
                                        type types-sros:port;
                                        description "Port identifier";
                                    }

                                    leaf dest-card {
                                        type int32;
                                        description "Card number";
                                    }

                                    leaf dest-fp {
                                        type int32;
                                        description "FP number";
                                    }

                                    leaf dest-tap-offset {
                                        type int32;
                                        description "Destination TAP.";
                                    }

                                    leaf adapted-admin-mbs {
                                        type int64;
                                        units "bytes";
                                        description "Admin MBS.";
                                    }

                                    leaf adapted-admin-cbs {
                                        type int64;
                                        units "bytes";
                                        description "Admin CBS.";
                                    }

                                    leaf operational-mbs {
                                        type int64;
                                        units "bytes";
                                        description "Oper MBS.";
                                    }

                                    leaf depth {
                                        type union {
                                            type enumeration {
                                                enum max                            { value -1; }
                                            }
                                            type int64;
                                        }
                                        description "Depth CIR.";
                                    }

                                    leaf operational-cir {
                                        type union {
                                            type enumeration {
                                                enum max                            { value -1; }
                                            }
                                            type int64;
                                        }
                                        description "Oper CIR.";
                                    }

                                    leaf operational-fir {
                                        type union {
                                            type enumeration {
                                                enum max                            { value -1; }
                                            }
                                            type int64;
                                        }
                                        description "Oper FIR.";
                                    }

                                    leaf operational-pir {
                                        type union {
                                            type enumeration {
                                                enum max                            { value -1; }
                                            }
                                            type int64;
                                        }
                                        description "Oper PIR.";
                                    }

                                    leaf exceed-droptail {
                                        type union {
                                            type int64 {
                                                range "0..max";
                                            }
                                            type enumeration {
                                                enum auto                           { value -1; }
                                            }
                                        }
                                        description "Exceed droptail.";
                                    }

                                    leaf high-droptail {
                                        type union {
                                            type int64 {
                                                range "0..max";
                                            }
                                            type enumeration {
                                                enum auto                           { value -1; }
                                            }
                                        }
                                        description "High droptail.";
                                    }

                                    leaf high-plus-droptail {
                                        type union {
                                            type int64 {
                                                range "0..max";
                                            }
                                            type enumeration {
                                                enum auto                           { value -1; }
                                            }
                                        }
                                        description "Highplus droptail.";
                                    }

                                    leaf low-droptail {
                                        type union {
                                            type int64 {
                                                range "0..max";
                                            }
                                            type enumeration {
                                                enum auto                           { value -1; }
                                            }
                                        }
                                        description "Low droptail.";
                                    }

                                    leaf operational-exceed-burst {
                                        type types-qos:int64-max;
                                        description "Oper burst exceed.";
                                    }

                                    leaf operational-max-transmit-data-size {
                                        type types-qos:int64-max;
                                        description "Oper max transmit data size.";
                                    }

                                    leaf operational-burst-fir {
                                        type types-qos:int64-max;
                                        description "Oper burst FIR.";
                                    }

                                    leaf local-parent-rate {
                                        type types-qos:kbps;
                                        description "The local limit rate for the delay budget";
                                    }

                                } // list hardware-queue

                            } // list queue

                            list policer {
                                key "policer-id";
                                description "Enter the policer list instance";

                                leaf policer-id {
                                    type types-qos:ingress-policer-id;
                                    description "The unique identifier for the policer.";
                                }

                                container statistics {
                                    description "Enter the statistics context";

                                    choice stat-mode {
                                        case minimal {

                                            container minimal {
                                                description "Enter the minimal context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf all-dropped-packets {
                                                    type yang:counter64;
                                                    description "The number of all the priority packets dropped by the packet processor to traffic manager";
                                                }

                                                leaf all-dropped-octets {
                                                    type yang:counter64;
                                                    description "The number of all the priority octets dropped by the packet processor to traffic manager";
                                                }

                                                leaf all-forwarded-packets {
                                                    type yang:counter64;
                                                    description "The number of all the priority packets forwarded by the packet processor to traffic manager";
                                                }

                                                leaf all-forwarded-octets {
                                                    type yang:counter64;
                                                    description "The number of all the priority octets forwarded by the packet processor to traffic manager";
                                                }

                                            } // container minimal

                                        }
                                        case offered-profile-no-cir {

                                            container offered-profile-no-cir {
                                                description "Enter the offered-profile-no-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-no-cir

                                        }
                                        case offered-priority-no-cir {

                                            container offered-priority-no-cir {
                                                description "Enter the offered-priority-no-cir context";

                                                leaf high-priority-offered-packets {
                                                    type yang:counter64;
                                                    description "The number of high-priority packets offered by the packet processor to traffic manager";
                                                }

                                                leaf high-priority-offered-octets {
                                                    type yang:counter64;
                                                    description "The number of high-priority octets offered by the packet processor to traffic manager";
                                                }

                                                leaf low-priority-offered-packets {
                                                    type yang:counter64;
                                                    description "The number of low-priority packets offered by the packet processor to traffic manager";
                                                }

                                                leaf low-priority-offered-octets {
                                                    type yang:counter64;
                                                    description "The number of low-priority octets offered by the packet processor to traffic manager";
                                                }

                                                leaf high-priority-dropped-packets {
                                                    type yang:counter64;
                                                    description "The number of high-priority packets dropped by the packet processor to traffic manager";
                                                }

                                                leaf high-priority-dropped-octets {
                                                    type yang:counter64;
                                                    description "The number of high-priority octets dropped by the packet processor to traffic manager";
                                                }

                                                leaf low-priority-dropped-packets {
                                                    type yang:counter64;
                                                    description "The number of low-priority packets dropped by the packet processor to traffic manager";
                                                }

                                                leaf low-priority-dropped-octets {
                                                    type yang:counter64;
                                                    description "The number of low-priority octets dropped by the packet processor to traffic manager";
                                                }

                                                leaf high-priority-forwarded-packets {
                                                    type yang:counter64;
                                                    description "The number of high-priority packets forwarded by the packet processor to traffic manager";
                                                }

                                                leaf high-priority-forwarded-octets {
                                                    type yang:counter64;
                                                    description "The number of high-priority octets forwarded by the packet processor to traffic manager";
                                                }

                                                leaf low-priority-forwarded-packets {
                                                    type yang:counter64;
                                                    description "The number of low-priority packets forwarded by the packet processor to traffic manager";
                                                }

                                                leaf low-priority-forwarded-octets {
                                                    type yang:counter64;
                                                    description "The number of low-priority octets forwarded by the packet processor to traffic manager";
                                                }

                                            } // container offered-priority-no-cir

                                        }
                                        case offered-profile-cir {

                                            container offered-profile-cir {
                                                description "Enter the offered-profile-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-cir

                                        }
                                        case offered-priority-cir {

                                            container offered-priority-cir {
                                                description "Enter the offered-priority-cir context";

                                                leaf high-priority-offered-packets {
                                                    type yang:counter64;
                                                    description "The number of high-priority packets offered by the packet processor to traffic manager";
                                                }

                                                leaf high-priority-offered-octets {
                                                    type yang:counter64;
                                                    description "The number of high-priority octets offered by the packet processor to traffic manager";
                                                }

                                                leaf low-priority-offered-packets {
                                                    type yang:counter64;
                                                    description "The number of low-priority packets offered by the packet processor to traffic manager";
                                                }

                                                leaf low-priority-offered-octets {
                                                    type yang:counter64;
                                                    description "The number of low-priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-priority-cir

                                        }
                                        case offered-total-cir {

                                            container offered-total-cir {
                                                description "Enter the offered-total-cir context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-total-cir

                                        }
                                        case offered-limited-profile-cir {

                                            container offered-limited-profile-cir {
                                                description "Enter the offered-limited-profile-cir context";

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-limited-profile-cir

                                        }
                                        case offered-profile-capped-cir {

                                            container offered-profile-capped-cir {
                                                description "Enter the offered-profile-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-capped-cir

                                        }
                                        case offered-profile-with-discards {

                                            container offered-profile-with-discards {
                                                description "Enter the offered-profile-with-discards context";

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-profile packets forwarded by the packet processor to traffic manager";
                                                }

                                                leaf out-profile-forwarded-octets {
                                                    type yang:counter64;
                                                    description "The number of out-profile octets forwarded by the packet processor to traffic manager";
                                                }

                                                leaf dropped-exceed-profile-packets {
                                                    type yang:counter64;
                                                    description "The number of dropped-exceed-profile packets by the packet processor to traffic manager";
                                                }

                                                leaf dropped-exceed-profile-octets {
                                                    type yang:counter64;
                                                    description "The number of dropped-exceed-profile octets by the packet processor to traffic manager";
                                                }

                                            } // container offered-profile-with-discards

                                        }
                                        case offered-limited-capped-cir {

                                            container offered-limited-capped-cir {
                                                description "Enter the offered-limited-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf uncolor-offered-packets {
                                                    type yang:counter64;
                                                    description "The number of out-of-rofile packets offered by the packet processor to traffic manager";
                                                }

                                                leaf uncolor-offered-octets {
                                                    type yang:counter64;
                                                    description "The number of out-of-profile octets offered by the packet processor to traffic manager";
                                                }

                                            } // container offered-limited-capped-cir

                                        }
                                        case v4-v6 {

                                            container v4-v6 {
                                                description "Enter the v4-v6 context";

                                                leaf ipv4-offered-packets {
                                                    type yang:counter64;
                                                    description "The number of ipv4 packets offered by the packet processor to traffic manager";
                                                }

                                                leaf ipv4-offered-octets {
                                                    type yang:counter64;
                                                    description "The number of ipv4 octets offered by the packet processor to traffic manager";
                                                }

                                                leaf ipv6-offered-packets {
                                                    type yang:counter64;
                                                    description "The number of ipv6 packets offered by the packet processor to traffic manager";
                                                }

                                                leaf ipv6-offered-octets {
                                                    type yang:counter64;
                                                    description "The number of ipv6 octets offered by the packet processor to traffic manager";
                                                }

                                                leaf ipv4-dropped-packets {
                                                    type yang:counter64;
                                                    description "The number of ipv4 packets dropped by the packet processor to traffic manager";
                                                }

                                                leaf ipv4-dropped-octets {
                                                    type yang:counter64;
                                                    description "The number of ipv4 octets dropped by the packet processor to traffic manager";
                                                }

                                                leaf ipv6-dropped-packets {
                                                    type yang:counter64;
                                                    description "The number of ipv6 packets dropped by the packet processor to traffic manager";
                                                }

                                                leaf ipv6-dropped-octets {
                                                    type yang:counter64;
                                                    description "The number of ipv6 octets dropped by the packet processor to traffic manager";
                                                }

                                                leaf ipv4-forwarded-packets {
                                                    type yang:counter64;
                                                    description "The number of ipv4 packets forwarded by the packet processor to traffic manager";
                                                }

                                                leaf ipv4-forwarded-octets {
                                                    type yang:counter64;
                                                    description "The number of ipv4 octets forwarded by the packet processor to traffic manager";
                                                }

                                                leaf ipv6-forwarded-packets {
                                                    type yang:counter64;
                                                    description "The number of ipv6 packets forwarded by the packet processor to traffic manager";
                                                }

                                                leaf ipv6-forwarded-octets {
                                                    type yang:counter64;
                                                    description "The number of ipv6 octets forwarded by the packet processor to traffic manager";
                                                }

                                            } // container v4-v6

                                        }
                                        case ecn-marked {

                                            container ecn-marked {
                                                description "Enter the ecn-marked context";

                                                leaf all-offered-packets {
                                                    type yang:counter64;
                                                    description "The number of packets offered by the packet processor to traffic manager";
                                                }

                                                leaf all-offered-octets {
                                                    type yang:counter64;
                                                    description "The number of octets offered by the packet processor to traffic manager";
                                                }

                                                leaf all-dropped-packets {
                                                    type yang:counter64;
                                                    description "The number of packets dropped by the packet processor to traffic manager";
                                                }

                                                leaf all-dropped-octets {
                                                    type yang:counter64;
                                                    description "The number of octets dropped by the packet processor to traffic manager";
                                                }

                                                leaf ecn-unmarked-forwarded-packets {
                                                    type yang:counter64;
                                                    description "The number of forwarded packets that were not ECN-marked (CE codepoint not set) by the policer";
                                                }

                                                leaf ecn-unmarked-forwarded-octets {
                                                    type yang:counter64;
                                                    description "The number of forwarded octets that were not ECN-marked (CE codepoint not set) by the policer";
                                                }

                                                leaf ecn-marked-forwarded-packets {
                                                    type yang:counter64;
                                                    description "The number of forwarded packets that were ECN-marked (CE codepoint set) by the policer";
                                                }

                                                leaf ecn-marked-forwarded-octets {
                                                    type yang:counter64;
                                                    description "The number of forwarded octets that were ECN-marked (CE codepoint set) by the policer";
                                                }

                                            } // container ecn-marked

                                        }
                                        case ecn-codepoints {

                                            container ecn-codepoints {
                                                description "Enter the ecn-codepoints context";

                                                leaf l4s-offered-packets {
                                                    type yang:counter64;
                                                    description "The number of L4S (ECT(1)) packets offered by the packet processor to traffic manager";
                                                }

                                                leaf l4s-offered-octets {
                                                    type yang:counter64;
                                                    description "The number of L4S (ECT(1)) octets offered by the packet processor to traffic manager";
                                                }

                                                leaf l4s-dropped-packets {
                                                    type yang:counter64;
                                                    description "The number of L4S (ECT(1)) packets dropped by the packet processor to traffic manager";
                                                }

                                                leaf l4s-dropped-octets {
                                                    type yang:counter64;
                                                    description "The number of L4S (ECT(1)) octets dropped by the packet processor to traffic manager";
                                                }

                                                leaf l4s-forwarded-packets {
                                                    type yang:counter64;
                                                    description "The number of L4S (ECT(1)) packets forwarded by the packet processor to traffic manager";
                                                }

                                                leaf l4s-forwarded-octets {
                                                    type yang:counter64;
                                                    description "The number of L4S (ECT(1)) octets forwarded by the packet processor to traffic manager";
                                                }

                                                leaf ce-offered-packets {
                                                    type yang:counter64;
                                                    description "The number of CE-marked packets offered by the packet processor to traffic manager";
                                                }

                                                leaf ce-offered-octets {
                                                    type yang:counter64;
                                                    description "The number of CE-marked octets offered by the packet processor to traffic manager";
                                                }

                                                leaf ce-dropped-packets {
                                                    type yang:counter64;
                                                    description "The number of CE-marked packets dropped by the packet processor to traffic manager";
                                                }

                                                leaf ce-dropped-octets {
                                                    type yang:counter64;
                                                    description "The number of CE-marked octets dropped by the packet processor to traffic manager";
                                                }

                                                leaf ce-forwarded-packets {
                                                    type yang:counter64;
                                                    description "The number of CE-marked packets forwarded by the packet processor to traffic manager";
                                                }

                                                leaf ce-forwarded-octets {
                                                    type yang:counter64;
                                                    description "The number of CE-marked octets forwarded by the packet processor to traffic manager";
                                                }

                                                leaf non-ect-offered-packets {
                                                    type yang:counter64;
                                                    description "The number of NonECT (Non-ECN-Capable-Transport) packets offered by the packet processor to traffic manager";
                                                }

                                                leaf non-ect-offered-octets {
                                                    type yang:counter64;
                                                    description "The number of NonECT octets offered by the packet processor to traffic manager";
                                                }

                                                leaf non-ect-dropped-packets {
                                                    type yang:counter64;
                                                    description "The number of NonECT packets dropped by the packet processor to traffic manager";
                                                }

                                                leaf non-ect-dropped-octets {
                                                    type yang:counter64;
                                                    description "The number of NonECT octets dropped by the packet processor to traffic manager";
                                                }

                                                leaf non-ect-forwarded-packets {
                                                    type yang:counter64;
                                                    description "The number of NonECT packets forwarded by the packet processor to traffic manager";
                                                }

                                                leaf non-ect-forwarded-octets {
                                                    type yang:counter64;
                                                    description "The number of NonECT octets forwarded by the packet processor to traffic manager";
                                                }

                                                leaf classic-ecn-offered-packets {
                                                    type yang:counter64;
                                                    description "The number of Classic ECN-Capable-Transport (ECT(0)) packets offered by the packet processor to traffic manager";
                                                }

                                                leaf classic-ecn-offered-octets {
                                                    type yang:counter64;
                                                    description "The number of Classic ECN-Capable-Transport (ECT(0)) octets offered by the packet processor to traffic manager";
                                                }

                                                leaf classic-ecn-dropped-packets {
                                                    type yang:counter64;
                                                    description "The number of Classic ECN-Capable-Transport (ECT(0)) packets dropped by the packet processor to traffic manager";
                                                }

                                                leaf classic-ecn-dropped-octets {
                                                    type yang:counter64;
                                                    description "The number of Classic ECN-Capable-Transport (ECT(0)) octets dropped by the packet processor to traffic manager";
                                                }

                                                leaf classic-ecn-forwarded-packets {
                                                    type yang:counter64;
                                                    description "The number of Classic ECN-Capable-Transport (ECT(0)) packets forwarded by the packet processor to traffic manager";
                                                }

                                                leaf classic-ecn-forwarded-octets {
                                                    type yang:counter64;
                                                    description "The number of Classic ECN-Capable-Transport (ECT(0)) octets forwarded by the packet processor to traffic manager";
                                                }

                                            } // container ecn-codepoints

                                        }
                                    }
                                } // container statistics

                                list hardware-policer {
                                    key "source-card source-fp source-port";
                                    description "Enter the hardware-policer list instance";

                                    leaf source-card {
                                        type int32;
                                        description "Card number";
                                    }

                                    leaf source-fp {
                                        type int32;
                                        description "FP number";
                                    }

                                    leaf source-port {
                                        type types-sros:port;
                                        description "Port identifier";
                                    }

                                    leaf adapted-admin-cbs {
                                        type int64;
                                        units "bytes";
                                        description "Admin CBS.";
                                    }

                                    leaf adapted-admin-mbs {
                                        type int64;
                                        units "bytes";
                                        description "Admin MBS.";
                                    }

                                    leaf adapted-hp-only {
                                        type int64;
                                        units "bytes";
                                        description "Hi Prio Only.";
                                    }

                                    leaf depth {
                                        type int64;
                                        units "bytes";
                                        description "Depth.";
                                    }

                                    leaf operational-cir {
                                        type types-qos:int64-max;
                                        description "Oper CIR.";
                                    }

                                    leaf operational-fir {
                                        type types-qos:int64-max;
                                        description "Oper FIR.";
                                    }

                                    leaf operational-pir {
                                        type types-qos:int64-max;
                                        description "Oper PIR.";
                                    }

                                } // list hardware-policer

                            } // list policer

                        } // container sap-ingress

                    } // container qos

                } // container ingress

                container egress {
                    description "Enter the egress context";

                    container qos {
                        description "Enter the qos context";

                        container sap-egress {
                            description "Enter the sap-egress context";

                            container traffic-manager {
                                description "Enter the traffic-manager context";

                                container statistics {
                                    description "Enter the statistics context";

                                    leaf in-inplus-profile-dropped-packets {
                                        type yang:counter64;
                                        description
                                            "The number of in-profile packets
                                             discarded by the egress traffic manager due
                                             to: MBS exceeded, buffer pool limit
                                             exceeded, etc.";
                                    }

                                    leaf in-inplus-profile-dropped-octets {
                                        type yang:counter64;
                                        description
                                            "The number of in-profile octets
                                             discarded by the egress traffic manager due
                                             to: MBS exceeded, buffer pool limit
                                             exceeded, etc.";
                                    }

                                    leaf out-exceed-profile-dropped-packets {
                                        type yang:counter64;
                                        description
                                            "The number of out-of-profile packets
                                             discarded by the egress traffic manager due
                                             to: MBS exceeded, buffer pool limit
                                             exceeded, etc.";
                                    }

                                    leaf out-exceed-profile-dropped-octets {
                                        type yang:counter64;
                                        description
                                            "The number of out-of-profile packets
                                             discarded by the egress traffic manager due
                                             to: MBS exceeded, buffer pool limit
                                             exceeded, etc.";
                                    }

                                    leaf in-inplus-profile-forwarded-packets {
                                        type yang:counter64;
                                        description
                                            "The number of in-profile packets
                                             (rate below CIR) forwarded by the
                                             egress traffic manager.";
                                    }

                                    leaf in-inplus-profile-forwarded-octets {
                                        type yang:counter64;
                                        description
                                            "The number of in-profile octets
                                             (rate below CIR) forwarded by the
                                             egress traffic manager.";
                                    }

                                    leaf out-exceed-profile-forwarded-packets {
                                        type yang:counter64;
                                        description
                                            "The number of out-of-profile packets
                                             (rate above CIR) forwarded by the
                                             egress traffic manager.";
                                    }

                                    leaf out-exceed-profile-forwarded-octets {
                                        type yang:counter64;
                                        description
                                            "The number of out-of-profile octets
                                             (rate above CIR) forwarded by the
                                             egress traffic manager.";
                                    }

                                    leaf aggregate-forwarded-packets {
                                        type yang:counter64;
                                        description
                                            "The aggregate number of in and out-of profile
                                             packets forwarded by the egress traffic manager.";
                                    }

                                    leaf aggregate-forwarded-octets {
                                        type yang:counter64;
                                        description
                                            "The aggregate number of in and out-of profile
                                             octets forwarded by the egress traffic manager.";
                                    }

                                    leaf aggregate-dropped-packets {
                                        type yang:counter64;
                                        description
                                            "The aggregate number of in and out-of profile
                                             packets discarded by the egress traffic manager due
                                             to: MBS exceeded, buffer pool limit
                                             exceeded, etc.";
                                    }

                                    leaf aggregate-dropped-octets {
                                        type yang:counter64;
                                        description
                                            "The aggregate number of in and out-of profile
                                             octets discarded by the egress traffic manager due
                                             to: MBS exceeded, buffer pool limit
                                             exceeded, etc.";
                                    }

                                    leaf last-cleared-time {
                                        type yang:date-and-time;
                                        description "Time when the counters in this table were last cleared.";
                                    }

                                } // container statistics

                            } // container traffic-manager

                            container aggregate-shapers {
                                description "Enter the aggregate-shapers context";

                                list aggregate-shaper-port {
                                    key "port-id";
                                    description "Enter the aggregate-shaper-port list instance";

                                    leaf port-id {
                                        type types-sros:port;
                                        description "The identifier which uniquely identifies the port.";
                                    }

                                    leaf burst-limit {
                                        type int32;
                                        units "bytes";
                                        description "Operational burst";
                                    }

                                    leaf depth {
                                        type uint32;
                                        units "bytes";
                                        description "Leaky-bucket depth of the aggregate shaper PIR";
                                    }

                                    leaf packet-mode {
                                        type types-qos:packet-mode;
                                        description "Packet-mode";
                                    }

                                    leaf out-of-date {
                                        type boolean;
                                        description
                                            "Info is out-of-date with respect to the latest config; the
                                             shaper-algorithm still needs to re-calculate the implemented
                                             rate.";
                                    }

                                    leaf queue-set-size {
                                        type int32;
                                        description "Queue set size";
                                    }

                                    leaf queue-set-size-overridden {
                                        type boolean;
                                        description
                                            "Info queue-set-size-overridden is set to true when the shaper is created by
                                             the override configured for sap egress qos policy. When it is set to false,
                                             it indicates that fp-resource-policy default-size setting is used to create
                                             this shaper.";
                                    }

                                    container rate {
                                        description "Enter the rate context";

                                        leaf assigned {
                                            type uint32;
                                            units "kilobps";
                                            description "Rate assigned by a hw-agg-shaper-scheduler";
                                        }

                                        leaf implemented {
                                            type uint32;
                                            units "kilobps";
                                            description
                                                "Implemented rate (based on hardware restrictions and based
                                                 on avg-frame-overhead and ATM adjustments)";
                                        }

                                        leaf consumed {
                                            type uint32;
                                            units "kilobps";
                                            description
                                                "Sum of the rates of the queues feeding into the aggregate
                                                 shaper";
                                        }

                                    } // container rate

                                    container avg-frame-overhead {
                                        description "Enter the avg-frame-overhead context";

                                        leaf overhead {
                                            type decimal64 {
                                                fraction-digits 2;
                                            }
                                            units "percent";
                                            description "Percentage average frame overhead";
                                        }

                                        leaf real-time {
                                            type boolean;
                                            description "Is it real-time?";
                                        }

                                    } // container avg-frame-overhead

                                    container hw-agg-shaper-scheduler {
                                        description "Enter the hw-agg-shaper-scheduler context";

                                        leaf active {
                                            type boolean;
                                            description
                                                "The aggregate shaper is controlled by a
                                                 hw-agg-shaper-scheduler";
                                        }

                                        leaf running {
                                            type boolean;
                                            description
                                                "The hw-agg-shaper-scheduler is currently running and
                                                 updating the aggregate shaper rates";
                                        }

                                        leaf invalid-class-usage {
                                            type boolean;
                                            description
                                                "The aggregate shaper has queues in multiple classes in the
                                                 same group in the hw-agg-shaper-scheduler";
                                        }

                                    } // container hw-agg-shaper-scheduler

                                } // list aggregate-shaper-port

                            } // container aggregate-shapers

                            list queue {
                                key "queue-id";
                                description "Enter the queue list instance";

                                leaf queue-id {
                                    type types-qos:egress-queue-id;
                                    description "The unique identifier for the queue.";
                                }

                                container queue-depth {
                                    description "Enter the queue-depth context";

                                    leaf elapsed-time {
                                        type types-sros:time-interval;
                                        description "Indicated the elapsed time.";
                                    }

                                    leaf depth-0-to-10-percent {
                                        type decimal64 {
                                            fraction-digits 2;
                                        }
                                        description "Indicated the depth 0 to 10 percent.";
                                    }

                                    leaf depth-11-to-20-percent {
                                        type decimal64 {
                                            fraction-digits 2;
                                        }
                                        description "Indicated the depth 0 to 20 percent.";
                                    }

                                    leaf depth-21-to-30-percent {
                                        type decimal64 {
                                            fraction-digits 2;
                                        }
                                        description "Indicated the depth 0 to 30 percent.";
                                    }

                                    leaf depth-31-to-40-percent {
                                        type decimal64 {
                                            fraction-digits 2;
                                        }
                                        description "Indicated the depth 0 to 40 percent.";
                                    }

                                    leaf depth-41-to-50-percent {
                                        type decimal64 {
                                            fraction-digits 2;
                                        }
                                        description "Indicated the depth 0 to 50 percent.";
                                    }

                                    leaf depth-51-to-60-percent {
                                        type decimal64 {
                                            fraction-digits 2;
                                        }
                                        description "Indicated the depth 0 to 60 percent.";
                                    }

                                    leaf depth-61-to-70-percent {
                                        type decimal64 {
                                            fraction-digits 2;
                                        }
                                        description "Indicated the depth 0 to 70 percent.";
                                    }

                                    leaf depth-71-to-80-percent {
                                        type decimal64 {
                                            fraction-digits 2;
                                        }
                                        description "Indicated the depth 0 to 80 percent.";
                                    }

                                    leaf depth-81-to-90-percent {
                                        type decimal64 {
                                            fraction-digits 2;
                                        }
                                        description "Indicated the depth 0 to 90 percent.";
                                    }

                                    leaf depth-91-to-100-percent {
                                        type decimal64 {
                                            fraction-digits 2;
                                        }
                                        description "Indicated the depth 0 to 100 percent.";
                                    }

                                    leaf queue-polling-interval {
                                        type types-sros:time-interval;
                                        description "Indicates the queue polling interval.";
                                    }

                                    leaf last-violation {
                                        type yang:date-and-time;
                                        description "Indicates the last violation time.";
                                    }

                                    leaf total-threshold-violations {
                                        type yang:counter32;
                                        description "Indicates the total threshold violations.";
                                    }

                                    leaf high-water-mark-polling-interval {
                                        type types-sros:time-duration;
                                        units "microseconds";
                                        description "Indicates the high water mark polling interval.";
                                    }

                                } // container queue-depth

                                container statistics {
                                    description "Enter the statistics context";

                                    choice stat-mode {
                                        case profile {

                                            container profile {
                                                description "Enter the profile context";

                                                leaf in-inplus-profile-forwarded-packets {
                                                    type yang:counter64;
                                                    description
                                                        "The number of in-profile/in-plus-profile packets
                                                         (rate below CIR) forwarded.";
                                                }

                                                leaf in-inplus-profile-forwarded-octets {
                                                    type yang:counter64;
                                                    description
                                                        "The number of in-profile/in-plus-profile octets
                                                         (rate below CIR) forwarded.";
                                                }

                                                leaf out-exceed-profile-forwarded-packets {
                                                    type yang:counter64;
                                                    description
                                                        "The number of out-profile/exceed-profile packets
                                                         (rate above CIR) forwarded.";
                                                }

                                                leaf out-exceed-profile-forwarded-octets {
                                                    type yang:counter64;
                                                    description
                                                        "The number of out-profile/exceed-profile octets
                                                         (rate above CIR) forwarded.";
                                                }

                                                leaf in-inplus-profile-dropped-packets {
                                                    type yang:counter64;
                                                    description
                                                        "The number of in-profile/in-plus-profile packets
                                                         discarded.";
                                                }

                                                leaf in-inplus-profile-dropped-octets {
                                                    type yang:counter64;
                                                    description
                                                        "The number of in-profile/in-plus-profile octets
                                                         discarded.";
                                                }

                                                leaf out-exceed-profile-dropped-packets {
                                                    type yang:counter64;
                                                    description
                                                        "The number of out-profile/exceed-profile packets
                                                         discarded.";
                                                }

                                                leaf out-exceed-profile-dropped-octets {
                                                    type yang:counter64;
                                                    description
                                                        "The number of out-profile/exceed-profile octets
                                                         discarded.";
                                                }

                                            } // container profile

                                        }
                                        case v4-v6 {

                                            container v4-v6 {
                                                description "Enter the v4-v6 context";

                                                leaf ipv4-dropped-packets {
                                                    type yang:counter64;
                                                    description "The number of ipv4 packets discarded.";
                                                }

                                                leaf ipv4-dropped-octets {
                                                    type yang:counter64;
                                                    description "The number of ipv4 octets discarded.";
                                                }

                                                leaf ipv6-dropped-packets {
                                                    type yang:counter64;
                                                    description "The number of ipv6 packets discarded.";
                                                }

                                                leaf ipv6-dropped-octets {
                                                    type yang:counter64;
                                                    description "The number of ipv6 octets discarded.";
                                                }

                                                leaf ipv4-forwarded-packets {
                                                    type yang:counter64;
                                                    description "The number of ipv4 packets forwarded.";
                                                }

                                                leaf ipv4-forwarded-octets {
                                                    type yang:counter64;
                                                    description "The number of ipv4 octets forwarded.";
                                                }

                                                leaf ipv6-forwarded-packets {
                                                    type yang:counter64;
                                                    description "The number of ipv6 packets forwarded.";
                                                }

                                                leaf ipv6-forwarded-octets {
                                                    type yang:counter64;
                                                    description "The number of ipv6 octets forwarded.";
                                                }

                                            } // container v4-v6

                                        }
                                        case ecn-marked {

                                            container ecn-marked {
                                                description "Enter the ecn-marked context";

                                                leaf ecn-unmarked-forwarded-packets {
                                                    type yang:counter64;
                                                    description
                                                        "The number of forwarded packets that were not ECN-marked
                                                         (CE codepoint not set).";
                                                }

                                                leaf ecn-unmarked-forwarded-octets {
                                                    type yang:counter64;
                                                    description
                                                        "The number of forwarded octets that were not ECN-marked
                                                         (CE codepoint not set).";
                                                }

                                                leaf ecn-marked-forwarded-packets {
                                                    type yang:counter64;
                                                    description
                                                        "The number of forwarded packets that were ECN-marked
                                                         (CE codepoint set).";
                                                }

                                                leaf ecn-marked-forwarded-octets {
                                                    type yang:counter64;
                                                    description
                                                        "The number of forwarded octets that were ECN-marked
                                                         (CE codepoint set).";
                                                }

                                                leaf dropped-packets {
                                                    type yang:counter64;
                                                    description "The number of packets discarded.";
                                                }

                                                leaf dropped-octets {
                                                    type yang:counter64;
                                                    description "The number of octets discarded.";
                                                }

                                            } // container ecn-marked

                                        }
                                        case mismatch {

                                            container mismatch {
                                                description "Enter the mismatch context";

                                                leaf in-inplus-profile-forwarded-packets {
                                                    type yang:counter64;
                                                    description
                                                        "The number of in-profile/in-plus-profile packets
                                                         (rate below CIR) forwarded.";
                                                }

                                                leaf in-inplus-profile-forwarded-octets {
                                                    type yang:counter64;
                                                    description
                                                        "The number of in-profile/in-plus-profile octets
                                                         (rate below CIR) forwarded.";
                                                }

                                                leaf out-exceed-profile-forwarded-packets {
                                                    type yang:counter64;
                                                    description
                                                        "The number of out-profile/exceed-profile packets
                                                         (rate above CIR) forwarded.";
                                                }

                                                leaf out-exceed-profile-forwarded-octets {
                                                    type yang:counter64;
                                                    description
                                                        "The number of out-profile/exceed-profile octets
                                                         (rate above CIR) forwarded.";
                                                }

                                                leaf in-inplus-profile-dropped-packets {
                                                    type yang:counter64;
                                                    description
                                                        "The number of in-profile/in-plus-profile packets
                                                         discarded.";
                                                }

                                                leaf in-inplus-profile-dropped-octets {
                                                    type yang:counter64;
                                                    description
                                                        "The number of in-profile/in-plus-profile octets
                                                         discarded.";
                                                }

                                                leaf out-exceed-profile-dropped-packets {
                                                    type yang:counter64;
                                                    description
                                                        "The number of out-profile/exceed-profile packets
                                                         discarded.";
                                                }

                                                leaf out-exceed-profile-dropped-octets {
                                                    type yang:counter64;
                                                    description
                                                        "The number of out-profile/exceed-profile octets
                                                         discarded.";
                                                }

                                            } // container mismatch

                                        }
                                    }
                                } // container statistics

                                list hardware-queue {
                                    key "source-card source-fp source-port";
                                    description "Enter the hardware-queue list instance";

                                    leaf source-card {
                                        type int32;
                                        description "Card number";
                                    }

                                    leaf source-fp {
                                        type int32;
                                        description "FP number";
                                    }

                                    leaf source-port {
                                        type types-sros:port;
                                        description "Port identifier";
                                    }

                                    leaf adapted-admin-mbs {
                                        type int64;
                                        units "bytes";
                                        description "Admin MBS.";
                                    }

                                    leaf exceed-droptail {
                                        type union {
                                            type int64 {
                                                range "0..max";
                                            }
                                            type enumeration {
                                                enum auto                           { value -1; }
                                            }
                                        }
                                        description "Exceed droptail.";
                                    }

                                    leaf high-droptail {
                                        type union {
                                            type int64 {
                                                range "0..max";
                                            }
                                            type enumeration {
                                                enum auto                           { value -1; }
                                            }
                                        }
                                        description "High droptail.";
                                    }

                                    leaf high-plus-droptail {
                                        type union {
                                            type int64 {
                                                range "0..max";
                                            }
                                            type enumeration {
                                                enum auto                           { value -1; }
                                            }
                                        }
                                        description "Highplus droptail.";
                                    }

                                    leaf low-droptail {
                                        type union {
                                            type int64 {
                                                range "0..max";
                                            }
                                            type enumeration {
                                                enum auto                           { value -1; }
                                            }
                                        }
                                        description "Low droptail.";
                                    }

                                    leaf operational-cbs {
                                        type int64;
                                        units "bytes";
                                        description "Oper CBS.";
                                    }

                                    leaf operational-cir {
                                        type union {
                                            type enumeration {
                                                enum max                            { value -1; }
                                            }
                                            type int64;
                                        }
                                        description "Oper CIR.";
                                    }

                                    leaf operational-mbs {
                                        type int64;
                                        units "bytes";
                                        description "Oper MBS.";
                                    }

                                    leaf operational-pir {
                                        type union {
                                            type enumeration {
                                                enum max                            { value -1; }
                                            }
                                            type int64;
                                        }
                                        description "Oper PIR.";
                                    }

                                    leaf depth {
                                        type union {
                                            type enumeration {
                                                enum max                            { value -1; }
                                            }
                                            type int64;
                                        }
                                        description "Depth CIR.";
                                    }

                                    leaf operational-burst-limit {
                                        type uint32;
                                        description "Sepcifies the operational burst-limit value.";
                                    }

                                    leaf operational-exceed-burst {
                                        type types-qos:int64-max;
                                        description "Oper burst exceed.";
                                    }

                                    leaf operational-max-transmit-data-size {
                                        type types-qos:int64-max;
                                        description "Oper max transmit data size.";
                                    }

                                    leaf operational-burst-fir {
                                        type types-qos:int64-max;
                                        description "Oper burst FIR.";
                                    }

                                    leaf orphan {
                                        type boolean;
                                        description "Orphan queue";
                                    }

                                    leaf local-parent-rate {
                                        type types-qos:kbps;
                                        description "The local limit rate for the delay budget";
                                    }

                                    container exceed-slope {
                                        description "Enter the exceed-slope context";

                                        leaf current-probability {
                                            type types-sros:percent;
                                            description "Specifies the current probability in percentage";
                                        }

                                    } // container exceed-slope

                                    container high-slope {
                                        description "Enter the high-slope context";

                                        leaf current-probability {
                                            type types-sros:percent;
                                            description "Specifies the current probability in percentage";
                                        }

                                    } // container high-slope

                                    container high-plus-slope {
                                        description "Enter the high-plus-slope context";

                                        leaf current-probability {
                                            type types-sros:percent;
                                            description "Specifies the current probability in percentage";
                                        }

                                    } // container high-plus-slope

                                    container low-slope {
                                        description "Enter the low-slope context";

                                        leaf current-probability {
                                            type types-sros:percent;
                                            description "Specifies the current probability in percentage";
                                        }

                                    } // container low-slope

                                    container aggregate-rate {
                                        description "Enter the aggregate-rate context";

                                        leaf rate {
                                            type types-qos:kbps;
                                            units "kilobps";
                                            description "Rate";
                                        }

                                        leaf on-the-wire {
                                            type types-qos:on-the-wire;
                                            description "On the wire";
                                        }

                                        leaf type {
                                            type types-qos:qos-location;
                                            description "Aggregate rate type";
                                        }

                                        leaf vport-rate {
                                            type types-qos:kbps;
                                            units "kilobps";
                                            description "Vport rate";
                                        }

                                    } // container aggregate-rate

                                } // list hardware-queue

                            } // list queue

                            list policer {
                                key "policer-id";
                                description "Enter the policer list instance";

                                leaf policer-id {
                                    type types-qos:sap-egress-policer-id;
                                    description "The unique identifier for the policer.";
                                }

                                container statistics {
                                    description "Enter the statistics context";

                                    choice stat-mode {
                                        case minimal {

                                            container minimal {
                                                description "Enter the minimal context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf all-dropped-packets {
                                                    type yang:counter64;
                                                    description "The number of all the priority packets dropped by the packet processor to traffic manager";
                                                }

                                                leaf all-dropped-octets {
                                                    type yang:counter64;
                                                    description "The number of all the priority octets dropped by the packet processor to traffic manager";
                                                }

                                                leaf all-forwarded-packets {
                                                    type yang:counter64;
                                                    description "The number of all the priority packets forwarded by the packet processor to traffic manager";
                                                }

                                                leaf all-forwarded-octets {
                                                    type yang:counter64;
                                                    description "The number of all the priority octets forwarded by the packet processor to traffic manager";
                                                }

                                            } // container minimal

                                        }
                                        case offered-profile-no-cir {

                                            container offered-profile-no-cir {
                                                description "Enter the offered-profile-no-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-no-cir

                                        }
                                        case offered-profile-cir {

                                            container offered-profile-cir {
                                                description "Enter the offered-profile-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-cir

                                        }
                                        case offered-total-cir {

                                            container offered-total-cir {
                                                description "Enter the offered-total-cir context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-total-cir

                                        }
                                        case offered-limited-capped-cir {

                                            container offered-limited-capped-cir {
                                                description "Enter the offered-limited-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf out-profile-offered-packets {
                                                    type yang:counter64;
                                                    description "The number of out-of-rofile packets offered by the packet processor to traffic manager";
                                                }

                                                leaf out-profile-offered-octets {
                                                    type yang:counter64;
                                                    description "The number of out-of-profile octets offered by the packet processor to traffic manager";
                                                }

                                            } // container offered-limited-capped-cir

                                        }
                                        case offered-profile-capped-cir {

                                            container offered-profile-capped-cir {
                                                description "Enter the offered-profile-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-capped-cir

                                        }
                                        case offered-total-cir-exceed {

                                            container offered-total-cir-exceed {
                                                description "Enter the offered-total-cir-exceed context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-total-cir-exceed

                                        }
                                        case offered-four-profile-no-cir {

                                            container offered-four-profile-no-cir {
                                                description "Enter the offered-four-profile-no-cir context";

                                                leaf inplus-profile-offered-packets {
                                                    type yang:counter64;
                                                    description "The number of inplus-profile packets offered by the packet processor to traffic manager";
                                                }

                                                leaf inplus-profile-offered-octets {
                                                    type yang:counter64;
                                                    description "The number of inplus-profile octets offered by the packet processor to traffic manager";
                                                }

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf exceed-profile-offered-packets {
                                                    type yang:counter64;
                                                    description "The number of exceed-profile packets offered by the packet processor to traffic manager";
                                                }

                                                leaf exceed-profile-offered-octets {
                                                    type yang:counter64;
                                                    description "The number of exceed-profile octets offered by the packet processor to traffic manager";
                                                }

                                                leaf inplus-profile-dropped-packets {
                                                    type yang:counter64;
                                                    description "The number of inplus-profile packets dropped by the packet processor to traffic manager";
                                                }

                                                leaf inplus-profile-dropped-octets {
                                                    type yang:counter64;
                                                    description "The number of inplus-profile octets dropped by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf inplus-profile-forwarded-packets {
                                                    type yang:counter64;
                                                    description "The number of inplus-profile packets forwarded by the packet processor to traffic manager";
                                                }

                                                leaf inplus-profile-forwarded-octets {
                                                    type yang:counter64;
                                                    description "The number of inplus-profile octets forwarded by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-four-profile-no-cir

                                        }
                                        case offered-total-cir-four-profile {

                                            container offered-total-cir-four-profile {
                                                description "Enter the offered-total-cir-four-profile context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf inplus-profile-dropped-packets {
                                                    type yang:counter64;
                                                    description "The number of inplus-profile packets dropped by the packet processor to traffic manager";
                                                }

                                                leaf inplus-profile-dropped-octets {
                                                    type yang:counter64;
                                                    description "The number of inplus-profile octets dropped by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf inplus-profile-forwarded-packets {
                                                    type yang:counter64;
                                                    description "The number of inplus-profile packets forwarded by the packet processor to traffic manager";
                                                }

                                                leaf inplus-profile-forwarded-octets {
                                                    type yang:counter64;
                                                    description "The number of inplus-profile octets forwarded by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-total-cir-four-profile

                                        }
                                        case v4-v6 {

                                            container v4-v6 {
                                                description "Enter the v4-v6 context";

                                                leaf ipv4-offered-packets {
                                                    type yang:counter64;
                                                    description "The number of ipv4 packets offered by the packet processor to traffic manager";
                                                }

                                                leaf ipv4-offered-octets {
                                                    type yang:counter64;
                                                    description "The number of ipv4 octets offered by the packet processor to traffic manager";
                                                }

                                                leaf ipv6-offered-packets {
                                                    type yang:counter64;
                                                    description "The number of ipv6 packets offered by the packet processor to traffic manager";
                                                }

                                                leaf ipv6-offered-octets {
                                                    type yang:counter64;
                                                    description "The number of ipv6 octets offered by the packet processor to traffic manager";
                                                }

                                                leaf ipv4-dropped-packets {
                                                    type yang:counter64;
                                                    description "The number of ipv4 packets dropped by the packet processor to traffic manager";
                                                }

                                                leaf ipv4-dropped-octets {
                                                    type yang:counter64;
                                                    description "The number of ipv4 octets dropped by the packet processor to traffic manager";
                                                }

                                                leaf ipv6-dropped-packets {
                                                    type yang:counter64;
                                                    description "The number of ipv6 packets dropped by the packet processor to traffic manager";
                                                }

                                                leaf ipv6-dropped-octets {
                                                    type yang:counter64;
                                                    description "The number of ipv6 octets dropped by the packet processor to traffic manager";
                                                }

                                                leaf ipv4-forwarded-packets {
                                                    type yang:counter64;
                                                    description "The number of ipv4 packets forwarded by the packet processor to traffic manager";
                                                }

                                                leaf ipv4-forwarded-octets {
                                                    type yang:counter64;
                                                    description "The number of ipv4 octets forwarded by the packet processor to traffic manager";
                                                }

                                                leaf ipv6-forwarded-packets {
                                                    type yang:counter64;
                                                    description "The number of ipv6 packets forwarded by the packet processor to traffic manager";
                                                }

                                                leaf ipv6-forwarded-octets {
                                                    type yang:counter64;
                                                    description "The number of ipv6 octets forwarded by the packet processor to traffic manager";
                                                }

                                            } // container v4-v6

                                        }
                                        case bonding {

                                            container bonding {
                                                description "Enter the bonding context";

                                                leaf connection-1-offered-packets {
                                                    type yang:counter64;
                                                    description "The number of connection-1 packets offered by the packet processor to traffic manager";
                                                }

                                                leaf connection-1-offered-octets {
                                                    type yang:counter64;
                                                    description "The number of connection-1 octets offered by the packet processor to traffic manager";
                                                }

                                                leaf connection-2-offered-packets {
                                                    type yang:counter64;
                                                    description "The number of connection-2 packets offered by the packet processor to traffic manager";
                                                }

                                                leaf connection-2-offered-octets {
                                                    type yang:counter64;
                                                    description "The number of connection-2 octets offered by the packet processor to traffic manager";
                                                }

                                                leaf connection-1-dropped-packets {
                                                    type yang:counter64;
                                                    description "The number of connection-1 packets dropped by the packet processor to traffic manager";
                                                }

                                                leaf connection-1-dropped-octets {
                                                    type yang:counter64;
                                                    description "The number of connection-1 octets dropped by the packet processor to traffic manager";
                                                }

                                                leaf connection-2-dropped-packets {
                                                    type yang:counter64;
                                                    description "The number of connection-2 packets dropped by the packet processor to traffic manager";
                                                }

                                                leaf connection-2-dropped-octets {
                                                    type yang:counter64;
                                                    description "The number of connection-2 octets dropped by the packet processor to traffic manager";
                                                }

                                                leaf connection-1-forwarded-packets {
                                                    type yang:counter64;
                                                    description "The number of connection-1 packets forwarded by the packet processor to traffic manager";
                                                }

                                                leaf connection-1-forwarded-octets {
                                                    type yang:counter64;
                                                    description "The number of connection-1 octets forwarded by the packet processor to traffic manager";
                                                }

                                                leaf connection-2-forwarded-packets {
                                                    type yang:counter64;
                                                    description "The number of connection-2 packets forwarded by the packet processor to traffic manager";
                                                }

                                                leaf connection-2-forwarded-octets {
                                                    type yang:counter64;
                                                    description "The number of connection-2 octets forwarded by the packet processor to traffic manager";
                                                }

                                            } // container bonding

                                        }
                                        case ecn-marked {

                                            container ecn-marked {
                                                description "Enter the ecn-marked context";

                                                leaf all-offered-packets {
                                                    type yang:counter64;
                                                    description "The number of packets offered by the packet processor to traffic manager";
                                                }

                                                leaf all-offered-octets {
                                                    type yang:counter64;
                                                    description "The number of octets offered by the packet processor to traffic manager";
                                                }

                                                leaf all-dropped-packets {
                                                    type yang:counter64;
                                                    description "The number of packets dropped by the packet processor to traffic manager";
                                                }

                                                leaf all-dropped-octets {
                                                    type yang:counter64;
                                                    description "The number of octets dropped by the packet processor to traffic manager";
                                                }

                                                leaf ecn-unmarked-forwarded-packets {
                                                    type yang:counter64;
                                                    description "The number of forwarded packets that were not ECN-marked (CE codepoint not set) by the policer";
                                                }

                                                leaf ecn-unmarked-forwarded-octets {
                                                    type yang:counter64;
                                                    description "The number of forwarded octets that were not ECN-marked (CE codepoint not set) by the policer";
                                                }

                                                leaf ecn-marked-forwarded-packets {
                                                    type yang:counter64;
                                                    description "The number of forwarded packets that were ECN-marked (CE codepoint set) by the policer";
                                                }

                                                leaf ecn-marked-forwarded-octets {
                                                    type yang:counter64;
                                                    description "The number of forwarded octets that were ECN-marked (CE codepoint set) by the policer";
                                                }

                                            } // container ecn-marked

                                        }
                                        case ecn-codepoints {

                                            container ecn-codepoints {
                                                description "Enter the ecn-codepoints context";

                                                leaf l4s-offered-packets {
                                                    type yang:counter64;
                                                    description "The number of L4S (ECT(1)) packets offered by the packet processor to traffic manager";
                                                }

                                                leaf l4s-offered-octets {
                                                    type yang:counter64;
                                                    description "The number of L4S (ECT(1)) octets offered by the packet processor to traffic manager";
                                                }

                                                leaf l4s-dropped-packets {
                                                    type yang:counter64;
                                                    description "The number of L4S (ECT(1)) packets dropped by the packet processor to traffic manager";
                                                }

                                                leaf l4s-dropped-octets {
                                                    type yang:counter64;
                                                    description "The number of L4S (ECT(1)) octets dropped by the packet processor to traffic manager";
                                                }

                                                leaf l4s-forwarded-packets {
                                                    type yang:counter64;
                                                    description "The number of L4S (ECT(1)) packets forwarded by the packet processor to traffic manager";
                                                }

                                                leaf l4s-forwarded-octets {
                                                    type yang:counter64;
                                                    description "The number of L4S (ECT(1)) octets forwarded by the packet processor to traffic manager";
                                                }

                                                leaf ce-offered-packets {
                                                    type yang:counter64;
                                                    description "The number of CE-marked packets offered by the packet processor to traffic manager";
                                                }

                                                leaf ce-offered-octets {
                                                    type yang:counter64;
                                                    description "The number of CE-marked octets offered by the packet processor to traffic manager";
                                                }

                                                leaf ce-dropped-packets {
                                                    type yang:counter64;
                                                    description "The number of CE-marked packets dropped by the packet processor to traffic manager";
                                                }

                                                leaf ce-dropped-octets {
                                                    type yang:counter64;
                                                    description "The number of CE-marked octets dropped by the packet processor to traffic manager";
                                                }

                                                leaf ce-forwarded-packets {
                                                    type yang:counter64;
                                                    description "The number of CE-marked packets forwarded by the packet processor to traffic manager";
                                                }

                                                leaf ce-forwarded-octets {
                                                    type yang:counter64;
                                                    description "The number of CE-marked octets forwarded by the packet processor to traffic manager";
                                                }

                                                leaf non-ect-offered-packets {
                                                    type yang:counter64;
                                                    description "The number of NonECT (Non-ECN-Capable-Transport) packets offered by the packet processor to traffic manager";
                                                }

                                                leaf non-ect-offered-octets {
                                                    type yang:counter64;
                                                    description "The number of NonECT octets offered by the packet processor to traffic manager";
                                                }

                                                leaf non-ect-dropped-packets {
                                                    type yang:counter64;
                                                    description "The number of NonECT packets dropped by the packet processor to traffic manager";
                                                }

                                                leaf non-ect-dropped-octets {
                                                    type yang:counter64;
                                                    description "The number of NonECT octets dropped by the packet processor to traffic manager";
                                                }

                                                leaf non-ect-forwarded-packets {
                                                    type yang:counter64;
                                                    description "The number of NonECT packets forwarded by the packet processor to traffic manager";
                                                }

                                                leaf non-ect-forwarded-octets {
                                                    type yang:counter64;
                                                    description "The number of NonECT octets forwarded by the packet processor to traffic manager";
                                                }

                                                leaf classic-ecn-offered-packets {
                                                    type yang:counter64;
                                                    description "The number of Classic ECN-Capable-Transport (ECT(0)) packets offered by the packet processor to traffic manager";
                                                }

                                                leaf classic-ecn-offered-octets {
                                                    type yang:counter64;
                                                    description "The number of Classic ECN-Capable-Transport (ECT(0)) octets offered by the packet processor to traffic manager";
                                                }

                                                leaf classic-ecn-dropped-packets {
                                                    type yang:counter64;
                                                    description "The number of Classic ECN-Capable-Transport (ECT(0)) packets dropped by the packet processor to traffic manager";
                                                }

                                                leaf classic-ecn-dropped-octets {
                                                    type yang:counter64;
                                                    description "The number of Classic ECN-Capable-Transport (ECT(0)) octets dropped by the packet processor to traffic manager";
                                                }

                                                leaf classic-ecn-forwarded-packets {
                                                    type yang:counter64;
                                                    description "The number of Classic ECN-Capable-Transport (ECT(0)) packets forwarded by the packet processor to traffic manager";
                                                }

                                                leaf classic-ecn-forwarded-octets {
                                                    type yang:counter64;
                                                    description "The number of Classic ECN-Capable-Transport (ECT(0)) octets forwarded by the packet processor to traffic manager";
                                                }

                                            } // container ecn-codepoints

                                        }
                                    }
                                } // container statistics

                                list hardware-policer {
                                    key "dest-card dest-fp dest-port";
                                    description "Enter the hardware-policer list instance";

                                    leaf dest-card {
                                        type int32;
                                        description "Card number";
                                    }

                                    leaf dest-fp {
                                        type int32;
                                        description "FP number";
                                    }

                                    leaf dest-port {
                                        type types-sros:port;
                                        description "Port identifier";
                                    }

                                    leaf adapted-admin-cbs {
                                        type int64;
                                        units "bytes";
                                        description "Admin CBS.";
                                    }

                                    leaf adapted-admin-mbs {
                                        type int64;
                                        units "bytes";
                                        description "Admin MBS.";
                                    }

                                    leaf adapted-hp-only {
                                        type int64;
                                        units "bytes";
                                        description "Hi Prio Only.";
                                    }

                                    leaf depth {
                                        type int64;
                                        units "bytes";
                                        description "Depth.";
                                    }

                                    leaf operational-cir {
                                        type types-qos:int64-max;
                                        description "Oper CIR.";
                                    }

                                    leaf operational-fir {
                                        type types-qos:int64-max;
                                        description "Oper FIR.";
                                    }

                                    leaf operational-pir {
                                        type types-qos:int64-max;
                                        description "Oper PIR.";
                                    }

                                } // list hardware-policer

                            } // list policer

                        } // container sap-egress

                    } // container qos

                } // container egress

                container lag {
                    description "Enter the lag context";

                    leaf active-port {
                        type types-sros:port;
                        description
                            "Port on the lag associated with this SAP, that is used when
                             lag-per-link-hash is enabled on the lag or when lag-link-map-profile
                             is configured on this SAP.";
                    }

                    container per-link-hash-oper {
                        description "Enter the per-link-hash-oper context";

                        leaf class {
                            type int32;
                            description "Operational value for class associated with this SAP.";
                        }

                        leaf weight {
                            type int32;
                            description "Operational value used for weight associated with this SAP.";
                        }

                        leaf is-overriden {
                            type boolean;
                            description
                                "Whether administrative values, subscriber management determined
                                 operational weight and class are used for this SAP.";
                        }

                    } // container per-link-hash-oper

                } // container lag

                container distributed-cpu-protection {
                    description "Enter the distributed-cpu-protection context";

                    list static-policer {
                        key "name card fp-number";
                        description "Enter the static-policer list instance";

                        leaf name {
                            type types-sros:named-item;
                            description "Name of static policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf total-exceed-count {
                            type uint64;
                            description "Total number of packets exceeding the policing parametersi.";
                        }

                        leaf exit-conform-state-count {
                            type uint32;
                            description "Total number of transition of the policer to the exceed state.";
                        }

                    } // list static-policer

                    list local-monitor-policer {
                        key "name card fp-number";
                        description "Enter the local-monitor-policer list instance";

                        leaf name {
                            type types-sros:named-item;
                            description "Name of local-monitor policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf all-dynamic-policer-allocation {
                            type boolean;
                            description "All dynamic-policers allocation status";
                        }

                        leaf total-exceed-count {
                            type uint64;
                            description "Total number of packets exceeding the policing parametersi.";
                        }

                        leaf exit-conform-state-count {
                            type uint32;
                            description "Total number of transition of the policer to the exceed state.";
                        }

                    } // list local-monitor-policer

                    list dynamic-policer {
                        key "protocol card fp-number";
                        description "Enter the dynamic-policer list instance";

                        leaf protocol {
                            type types-sros:dist-cpu-protection-protocol;
                            description "Dynamic policer protocol.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf dynamic-policer-allocation {
                            type boolean;
                            description "Dynamic-policer allocation status";
                        }

                        leaf total-exceed-count {
                            type uint64;
                            description "Total number of packets exceeding the policing parametersi.";
                        }

                        leaf exit-conform-state-count {
                            type uint32;
                            description "Total number of transition of the policer to the exceed state.";
                        }

                    } // list dynamic-policer

                } // container distributed-cpu-protection


            } // list sap

            list spoke-sdp {
                key "sdp-bind-id";
                description "Enter the spoke-sdp list instance";

                leaf sdp-bind-id {
                    type types-services:sdp-bind-id;
                    description
                        "SDP Binding identifier as <sdp-id>:<vc-id>.
                         sdp-id - [1..32767]
                         vc-id - [1..4294967295].";
                }

                leaf oper-state {
                    type enumeration {
                        enum up                             { value 1; }
                        enum down                           { value 5; }
                    }
                    description "Indicates the operating status of this Service-SDP binding.";
                }

                leaf oper-flags {
                    type bits {
                        bit sdp-bind-admin-down            { position 0; }
                        bit svc-admin-down                 { position 1; }
                        bit stitching-svc-txdown           { position 2; }
                        bit sdp-oper-down                  { position 3; }
                        bit sdp-path-mtu-too-small         { position 4; }
                        bit no-ingress-vc-label            { position 5; }
                        bit no-egress-vc-label             { position 6; }
                        bit svc-mtu-mismatch               { position 7; }
                        bit vc-type-mismatch               { position 8; }
                        bit relearn-limit-exceeded         { position 9; }
                        bit ies-if-admin-down              { position 10; }
                        bit released-ingress-vc-label      { position 11; }
                        bit labels-exhausted               { position 12; }
                        bit svc-param-mismatch             { position 13; }
                        bit insufficient-bandwidth         { position 14; }
                        bit pw-peer-fault-status-bits      { position 15; }
                        bit mesh-sdp-down                  { position 16; }
                        bit not-managed-by-mcring          { position 17; }
                        bit out-of-resource                { position 18; }
                        bit mh-standby                     { position 19; }
                        bit oam-down-mep-fault             { position 20; }
                        bit oam-up-mep-fault               { position 21; }
                        bit standby-sig-slave-tx-down      { position 22; }
                        bit oper-grp-down                  { position 23; }
                        bit withdrawn-ingress-vc-label     { position 24; }
                        bit vpls-pmsi-down                 { position 25; }
                        bit rec-prot-src-mac               { position 26; }
                        bit peer-fault-status-tx-down      { position 27; }
                        bit evpn-route-conflict            { position 28; }
                        bit admin-locked                   { position 29; }
                        bit evpn-p2mp-conflict             { position 30; }
                        bit label-stack-limit-exceeded     { position 31; }
                        bit vccv-bfd-down                  { position 32; }
                        bit stitching-svc-pw-fault         { position 33; }
                        bit out-of-anysec-resource         { position 34; }
                        bit anysec-service-and-tunnel-config-conflict { position 35; }
                        bit anysec-group-or-peer-oper-down { position 36; }
                    }
                    description
                        "This object indicates all the conditions that affect the
                         operating status of this SDP Bind.";
                }

                leaf pw-peer-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description
                        "Indicates bits set by the LDP peer when there is a fault on its
                         side of the pseudowire";
                }

                leaf pw-local-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description "Indicates locally set bits when there is a fault.";
                }

                leaf peer-vccv-cv-bits {
                    type bits {
                        bit icmp-ping                      { position 0; }
                        bit lsp-ping                       { position 1; }
                        bit bfd-fault-detection            { position 2; }
                        bit bfd-fault-detection-and-signalling { position 3; }
                    }
                    description "Indicates CV type bits set by the LDP peer if it supports VCCV.";
                }

                leaf peer-vccv-cc-bits {
                    type bits {
                        bit pwe3-control-word              { position 0; }
                        bit mpls-router-alert-label        { position 1; }
                        bit mpls-pw-demultiplex-or-label   { position 2; }
                    }
                    description "Indicates CC type bits set by the LDP peer if it supports VCCV.";
                }

                leaf oper-control-word {
                    type boolean;
                    description "Status of control word.";
                }

                leaf pw-fault-ip-address {
                    type types-sros:ip-address;
                    description "Faulty IP address sent by peer.";
                }

                leaf class-forwarding-oper-state {
                    type types-sros:oper-state;
                    description "Operational state of forwarding-class based forwarding on this SDP bind.";
                }

                leaf creation-origin {
                    type types-sros:creation-origin;
                    description "Creation origin of the service.";
                }

                leaf oper-hash-label {
                    type boolean;
                    description "Indicates the negotiated value of hash label that is used on this SDP binding.";
                }

                leaf min-required-sdp-oper-mtu {
                    type int32;
                    description "Minimum required SDP MTU size used with this SDP binding.";
                }

                leaf peer-ce-address {
                    type types-sros:ipv4-address;
                    description "IPv4 address of CE device that is learned via LDP on this SDP binding.";
                }

                container ingress {
                    description "Enter the ingress context";

                    leaf oper-label {
                        type uint32;
                        description "MPLS service label used by the far-end device to send packets to the local PEs sdp-bind.";
                    }

                    container statistics {
                        description "Enter the statistics context";

                        leaf forwarded-packets {
                            type yang:counter64;
                            description "Forwarded packets";
                        }

                        leaf forwarded-octets {
                            type yang:counter64;
                            description "Forwarded octets";
                        }

                        leaf dropped-packets {
                            type yang:counter64;
                            description "Dropped packets";
                        }

                        leaf dropped-octets {
                            type yang:counter64;
                            description "Dropped octets";
                        }

                    } // container statistics

                } // container ingress

                container egress {
                    description "Enter the egress context";

                    leaf oper-label {
                        type uint32;
                        description "MPLS service label used to send packets to the far-end device via this sdp-bind.";
                    }

                    container statistics {
                        description "Enter the statistics context";

                        leaf forwarded-packets {
                            type yang:counter64;
                            description "Forwarded packets";
                        }

                        leaf forwarded-octets {
                            type yang:counter64;
                            description "Forwarded octets";
                        }

                    } // container statistics

                } // container egress

            } // list spoke-sdp

        } // list ipipe

    } // grouping state-svc-ipipe

}
