submodule nokia-conf-router {

    yang-version "1.1";

    belongs-to nokia-conf { prefix "conf"; }

    import ietf-inet-types                { prefix "inet"; }
    import ietf-yang-types                { prefix "yang"; }
    import nokia-sros-yang-extensions     { prefix "sros-ext"; }
    import nokia-types-eth-cfm            { prefix "types-eth-cfm"; }
    import nokia-types-ipsec              { prefix "types-ipsec"; }
    import nokia-types-qos                { prefix "types-qos"; }
    import nokia-types-redundancy         { prefix "types-redundancy"; }
    import nokia-types-router             { prefix "types-router"; }
    import nokia-types-services           { prefix "types-services"; }
    import nokia-types-sros               { prefix "types-sros"; }

    include nokia-conf-eth-cfm;
    include nokia-conf-filter;
    include nokia-conf-filter-ip-exception;
    include nokia-conf-groups;
    include nokia-conf-ipsec;
    include nokia-conf-isa;
    include nokia-conf-isa-application-assurance-group;
    include nokia-conf-log;
    include nokia-conf-mcast-mgmt;
    include nokia-conf-policy-options;
    include nokia-conf-pxc;
    include nokia-conf-python;
    include nokia-conf-qos;
    include nokia-conf-redundancy;
    include nokia-conf-router-bgp;
    include nokia-conf-router-bier;
    include nokia-conf-router-dhcp-server;
    include nokia-conf-router-firewall;
    include nokia-conf-router-gtm;
    include nokia-conf-router-igmp;
    include nokia-conf-router-isis;
    include nokia-conf-router-l2tp;
    include nokia-conf-router-ldp;
    include nokia-conf-router-mld;
    include nokia-conf-router-mpls;
    include nokia-conf-router-msdp;
    include nokia-conf-router-nat;
    include nokia-conf-router-origin-validation;
    include nokia-conf-router-ospf;
    include nokia-conf-router-ospf3;
    include nokia-conf-router-p2mp-sr-tree;
    include nokia-conf-router-pcep;
    include nokia-conf-router-pim;
    include nokia-conf-router-radius;
    include nokia-conf-router-rib-api;
    include nokia-conf-router-rip;
    include nokia-conf-router-ripng;
    include nokia-conf-router-rsvp;
    include nokia-conf-router-segment-routing;
    include nokia-conf-router-static-route;
    include nokia-conf-router-twamp-light;
    include nokia-conf-router-wpp;
    include nokia-conf-routing-options;
    include nokia-conf-service;
    include nokia-conf-submgt-gtp;
    include nokia-conf-subscriber-mgmt;
    include nokia-conf-svc-nat;
    include nokia-conf-svc-vprn;
    include nokia-conf-system;
    include nokia-conf-system-security;
    include nokia-conf-test-oam;
    include nokia-conf-vrrp;

    sros-ext:sros-major-release "rel26";
    organization "Nokia";
    contact
        "Nokia SR OS Support
         Web: <http://www.nokia.com>";
    description
        "Nokia YANG Data model to configure routing protocols on SR OS based routers.

         Copyright 2016 Nokia. All rights reserved. Reproduction of this document
         is authorized on the condition that the foregoing copyright notice is included.

         This nokia-conf-router YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping conf-router {
        list router {
            key "router-name";
            max-elements 4;
            description "Enter the router list instance";

            leaf router-name {
                type types-sros:named-item-64 {
                    pattern ".{1,32}" {
                        error-message "'router-instance' must be 1 to 32 characters";
                    }
                }
                description "Administrative router name";
            }

            leaf description {
                when "not(../router-name = 'management')" {
                    description "not allowed in the management router";
                }
                type types-sros:description;
                description "Text description";
            }

            leaf triggered-policy {
                when "../router-name = 'Base'" {
                    description "only allowed in the Base router";
                }
                type boolean;
                default "false";
                description "Trigger route policy re-evaluation";
            }

            leaf allow-bgp-to-igp-export {
                when "../router-name = 'Base'" {
                    description "only allowed in the base router";
                }
                type boolean;
                default "true";
                description "Enable the distribution of BGP routes into the IGP";
            }

            leaf allow-icmp-redirect {
                when "../router-name = 'management'" {
                    description "only allowed in the management router";
                }
                type boolean;
                default "false";
                description "Allow ICMP redirects on the management interface";
            }

            leaf allow-icmp6-redirect {
                when "../router-name = 'management'" {
                    description "only allowed in the management router";
                }
                type boolean;
                default "false";
                description "Allow IPv6 ICMP redirects on the management interface";
            }

            leaf class-forwarding {
                when "../router-name = 'Base'" {
                    description "only allowed in the Base router";
                }
                type boolean;
                default "false";
                description "Allow class-based forwarding over IGP shortcuts";
            }

            leaf icmp-tunneling {
                when "../router-name = 'Base'" {
                    description "only allowed in the Base router";
                }
                type boolean;
                default "false";
                description "Allow tunneling of ICMP reply packets over MPLS LSPs";
            }

            leaf fib-telemetry {
                when "../router-name = 'Base'" {
                    description "only allowed in the Base router";
                }
                type boolean;
                default "false";
                description "Collect extra state information";
            }

            leaf selective-fib {
                when "../router-name = 'Base'" {
                    description "only allowed in the Base router";
                }
                type boolean;
                default "true";
                description "Enable selective FIB";
            }

            leaf autonomous-system {
                type uint32 {
                    range "1..max";
                }
                description "AS number advertised to peers for this router";
            }

            leaf ecmp {
                type types-router:ip-ecmp-128;
                default "1";
                description "Maximum equal-cost routes for routing table instance";
            }

            leaf entropy-label {
                type boolean;
                default "false";
                description "Use entropy label";
            }

            leaf fib-priority {
                type enumeration {
                    enum standard {
                        value 1;
                        description "Standard FIB priority for routing instances";
                    }
                    enum high {
                        value 2;
                        description "High FIB priority for routing instances";
                    }
                }
                default "standard";
                description "FIB priority for VPRN BGP routes";
            }

            leaf multicast-info-policy {
                type leafref {
                    path "../../multicast-management/multicast-info-policy/policy-name";
                }
                description "Multicast policy name for virtual router";
            }

            leaf router-id {
                type types-router:router-id;
                description "Unique router ID for the router in the AS";
            }

            leaf weighted-ecmp {
                type enumeration {
                    enum false                          { value 0; }
                    enum true                           { value 1; }
                    enum strict                         { value 2; }
                }
                default "false";
                description "Weighted load-balancing capability for ECMP routes";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container leak-export {
                when "../router-name = 'Base'" {
                    description "only allowed in the Base router";
                }
                description "Enter the leak-export context";

                leaf-list policy-name {
                    type union {
                        type types-sros:policy-expr-string;
                        type string;
                    }
                    max-elements 5;
                    ordered-by user;
                    description "Route policy name";
                }

                leaf leak-export-limit {
                    type uint32 {
                        range "1..10000";
                    }
                    default "5";
                    description "Maximum limit on number of GRT routes leaked into VPRNs";
                }

            } // container leak-export

            container gtp {
                when "../router-name = 'Base'" {
                    description "only allowed in the Base router";
                }
                description "Enter the gtp context";

                container s11 {
                    description "Enter the s11 context";

                    list interface {
                        key "interface-name";
                        description "Enter the interface list instance";

                        leaf interface-name {
                            type leafref {
                                path "../../../../interface/interface-name";
                            }
                            description "Name for the S11 interface";
                        }

                        leaf apn-policy {
                            type leafref {
                                path "../../../../../subscriber-mgmt/gtp/apn-policy/name";
                            }
                            description "Access point name policy for the S11 interface";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list interface

                    container peer-profile-map {
                        description "Enter the peer-profile-map context";

                        list prefix {
                            key "peer-prefix";
                            description "Enter the prefix list instance";

                            leaf peer-prefix {
                                type types-sros:ip-unicast-prefix;
                                description "IP prefix and prefix length for the subnet";
                            }

                            leaf peer-profile {
                                type leafref {
                                    path "../../../../../../subscriber-mgmt/gtp/peer-profile/name";
                                }
                                mandatory true;
                                description "GTP peer profile associated with the address prefix";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list prefix

                    } // container peer-profile-map

                } // container s11

                container upf-data-endpoint {
                    presence "Enable the upf-data-endpoint context";
                    description "Enable the upf-data-endpoint context";

                    leaf interface {
                        type leafref {
                            path "../../../interface/interface-name";
                        }
                        description "Interface on which the GTP-U packets terminate";
                    }

                    leaf fpe {
                        type leafref {
                            path "../../../../fwd-path-ext/fpe/fpe-id";
                        }
                        mandatory true;
                        description "FPE used to encapsulate and decapsulate GTP-U traffic";
                    }

                    leaf secondary-interface {
                        type leafref {
                            path "../../../../router/interface/interface-name";
                        }
                        description "Secondary interface on which GTP traffic terminates";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container upf-data-endpoint

                container uplink {
                    presence "Enable the uplink context";
                    description "Enable the uplink context";

                    leaf apn {
                        type string {
                            length "1..80";
                            pattern "([a-zA-Z0-9]+-+)*([a-zA-Z0-9]+\\.([a-zA-Z0-9]+-+)*)*[a-zA-Z0-9]+" {
                                error-message "'apn' must match APN format (e.g. internet.mnc123.mcc456.gprs)";
                            }
                        }
                        description "Network identifier part of the APN for the uplink";
                    }

                    leaf pdn-type {
                        type enumeration {
                            enum ipv4                           { value 0; }
                            enum ipv6                           { value 1; }
                            enum ipv4v6                         { value 2; }
                        }
                        default "ipv4";
                        description "Default PDN to be signaled in GTP";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container peer-profile-map {
                        description "Enter the peer-profile-map context";

                        list prefix {
                            key "peer-prefix";
                            description "Enter the prefix list instance";

                            leaf peer-prefix {
                                type types-sros:ip-unicast-prefix;
                                description "IP prefix and prefix length for the subnet";
                            }

                            leaf peer-profile {
                                type leafref {
                                    path "../../../../../../subscriber-mgmt/gtp/peer-profile/name";
                                }
                                mandatory true;
                                description "GTP peer profile associated with the address prefix";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list prefix

                    } // container peer-profile-map

                } // container uplink

            } // container gtp

            container bfd {
                when "../router-name = 'Base'" {
                    description "only allowed in the Base router";
                }
                description "Enter the bfd context";

                container seamless-bfd {
                    description "Enter the seamless-bfd context";

                    list peer {
                        key "address";
                        max-elements 8000;
                        description "Enter the peer list instance";

                        leaf address {
                            type types-sros:ip-unicast-address;
                            description "Address of the remote node";
                        }

                        leaf discriminator {
                            type uint32 {
                                range "1..4294967295";
                            }
                            description "Discriminator of the remote node";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list peer

                } // container seamless-bfd

            } // container bfd

            container dns {
                when "../router-name = 'Base'" {
                    description "Only allowed in the Base router";
                }
                description "Enter the dns context";

                container redirect-vprn {
                    description "Enter the redirect-vprn context";

                    list service {
                        key "service-name";
                        max-elements 1;
                        description "Enter the service list instance";

                        leaf service-name {
                            type leafref {
                                path "../../../../../service/vprn/service-name";
                            }
                            description "Administrative service name";
                        }

                        leaf preference {
                            type uint32 {
                                range "0..255";
                            }
                            description "Service preference";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list service

                } // container redirect-vprn

            } // container dns

            container evpn-neighbor-synchronization {
                presence "Enable the evpn-neighbor-synchronization context";
                description "Enable the evpn-neighbor-synchronization context";

                leaf admin-state {
                    type types-sros:admin-state;
                    default "disable";
                    description "Administrative state of EVPN synchronization";
                }

                leaf route-distinguisher {
                    type types-services:vpn-route-distinguisher;
                    sros-ext:auto-restart-to-modify;
                    description "Route distinguisher used for synchronization";
                }

                leaf evi-route-target {
                    type types-services:evi-route-target;
                    sros-ext:auto-restart-to-modify;
                    description "EVI route target to use for EVPN neighbor synchronization";
                }

                leaf route-tag {
                    type int32 {
                        range "1..255";
                    }
                    sros-ext:auto-restart-to-modify;
                    description "BGP route tag for MAC/IP routes synchronization";
                }

                leaf retention-timer {
                    type uint32 {
                        range "1..65535";
                    }
                    units "seconds";
                    description "Time that an EVPN ARP or ND entry is retained";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container evpn-neighbor-synchronization

            container aggregates {
                when "../router-name = 'Base'" {
                    description "only allowed in the Base router";
                }
                description "Enter the aggregates context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list aggregate {
                    key "ip-prefix";
                    description "Enter the aggregate list instance";

                    leaf ip-prefix {
                        type types-sros:ip-unicast-prefix;
                        description "Destination IP address prefix of the aggregate route";
                    }

                    leaf as-set {
                        type boolean;
                        default "false";
                        description "Use AS_SET path segment type for the aggregate route";
                    }

                    leaf-list community {
                        type types-sros:community;
                        max-elements 12;
                        ordered-by user;
                        description "Community name that is added to the aggregate route";
                    }

                    leaf description {
                        type types-sros:description;
                        description "Text description";
                    }

                    leaf summary-only {
                        type boolean;
                        default "false";
                        description "Advertise the aggregate route only";
                    }

                    leaf local-preference {
                        type int64 {
                            range "0..4294967295";
                        }
                        description "Local preference used when aggregate route is exported";
                    }

                    leaf discard-component-communities {
                        type boolean;
                        default "false";
                        description "Advertise aggregate with aggregate route community set";
                    }

                    leaf policy {
                        type leafref {
                            path "../../../../policy-options/policy-statement/name";
                        }
                        description "Policy name for the aggregated route";
                    }

                    leaf tunnel-group {
                        type types-redundancy:tunnel-group-id;
                        description "Tunnel group from which to associate the MC IPSec state";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice next-hop {
                        case blackhole {

                            container blackhole {
                                presence "Enable the blackhole context";
                                description "Enable the blackhole context";

                                leaf generate-icmp {
                                    type boolean;
                                    default "false";
                                    description "Send ICMP unreachable messages for aggregate routes";
                                }

                            } // container blackhole

                        }
                        case indirect {

                            leaf indirect {
                                type types-sros:ip-unicast-address;
                                sros-ext:immutable;
                                description "Address of the indirect next hop";
                            }

                        }
                    }
                    container aggregator {
                        description "Enter the aggregator context";

                        leaf as-number {
                            type uint32 {
                                range "1..max";
                            }
                            description "Aggregator AS number";
                        }

                        leaf address {
                            type types-sros:ipv4-unicast-address;
                            description "Aggregator IP address";
                        }

                    } // container aggregator

                } // list aggregate

            } // container aggregates

            container ipv6-te-router-id {
                when "../router-name = 'Base'" {
                    description "only allowed in the Base router";
                }
                description "Enter the ipv6-te-router-id context";

                leaf interface {
                    type leafref {
                        path "../../interface/interface-name";
                    }
                    description "Network IP interface name to obtain IP address";
                }

            } // container ipv6-te-router-id

            container mc-maximum-routes {
                description "Enter the mc-maximum-routes context";

                leaf value {
                    type int32 {
                        range "1..2147483647";
                    }
                    description "Maximum multicast routes configured on virtual router";
                }

                leaf log-only {
                    type boolean;
                    default "false";
                    description "Log and allow learning of new multicast routes";
                }

                leaf threshold {
                    type uint32 {
                        range "1..100";
                    }
                    units "percent";
                    description "Maximum multicast routes which the VRF holds";
                }

            } // container mc-maximum-routes

            container vrgw {
                when "../router-name = 'Base'" {
                    description "only allowed in the Base router";
                }
                description "Enter the vrgw context";

                container lanext {
                    presence "Enable the lanext context";
                    description "Enable the lanext context";

                    leaf admin-state {
                        type types-sros:admin-state;
                        default "disable";
                        description "Administrative state of Home LAN Extension";
                    }

                    leaf vxlan-port {
                        type uint32 {
                            range "4789|8472";
                        }
                        sros-ext:auto-restart-to-modify;
                        default "4789";
                        description "UDP port to be used by local or remote VXLAN VTEP";
                    }

                    leaf wlan-gw-group {
                        type leafref {
                            path "../../../../isa/wlan-gw-group/id";
                        }
                        sros-ext:immutable;
                        sros-ext:auto-restart-to-modify;
                        description "WLAN-GW group used for Home LAN Extension";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container vxlan-vtep-range {
                        description "Enter the vxlan-vtep-range context";

                        leaf start {
                            type types-sros:ip-unicast-without-local-address;
                            sros-ext:auto-restart-to-modify;
                            description "Lower bound of the VXLAN VTEP range";
                        }

                        leaf end {
                            type types-sros:ip-unicast-without-local-address;
                            sros-ext:auto-restart-to-modify;
                            description "Upper bound of the VXLAN VTEP range";
                        }

                    } // container vxlan-vtep-range


                } // container lanext

            } // container vrgw

            container wlan-gw {
                when "../router-name = 'Base'" {
                    description "only allowed in the Base router";
                }
                presence "Enable the wlan-gw context";
                description "Enable the wlan-gw context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container mobility-triggered-accounting {
                    description "Enter the mobility-triggered-accounting context";

                    leaf admin-state {
                        type types-sros:admin-state;
                        default "disable";
                        description "Administrative state of mobility triggered accounting";
                    }

                    leaf include-counters {
                        type boolean;
                        default "false";
                        description "Include counters in interim updates";
                    }

                    leaf hold-down {
                        type types-sros:time-duration {
                            range "60..86400";
                        }
                        units "seconds";
                        description "Hold additional mobility-triggered update until this timer expires";
                    }

                } // container mobility-triggered-accounting

                container distributed-subscriber-mgmt {
                    description "Enter the distributed-subscriber-mgmt context";

                    leaf ipv6-tcp-mss-adjust {
                        type uint32 {
                            range "160..10240";
                        }
                        description "TCP-MSS adjustment value in upstream direction for DSM";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }


                } // container distributed-subscriber-mgmt

                container xconnect {
                    description "Enter the xconnect context";

                    leaf admin-state {
                        type types-sros:admin-state;
                        default "disable";
                        description "Administrative state of the WLAN-GW cross-connect";
                    }

                    leaf tunnel-source-ip {
                        type types-sros:ipv6-prefix;
                        sros-ext:auto-restart-to-modify;
                        description "IPv6 address and prefix for the tunnel source";
                    }

                    leaf wlan-gw-group {
                        type leafref {
                            path "../../../../isa/wlan-gw-group/id";
                        }
                        sros-ext:auto-restart-to-modify;
                        description "ISA WLAN-GW Group";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container xconnect

            } // container wlan-gw

            container mss-adjust {
                presence "Enable the mss-adjust context";
                description "Enable the mss-adjust context";

                leaf nat-group {
                    type uint32;
                    sros-ext:immutable;
                    mandatory true;
                    description "NAT group used for TCP-MSS adjustment";
                }

                leaf segment-size {
                    type uint32 {
                        range "160..10240";
                    }
                    mandatory true;
                    description "TCP-MSS option value in transmitted TCP SYN requests";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container mss-adjust

            container reassembly {
                presence "Enable the reassembly context";
                description "Enable the reassembly context";

                leaf nat-group {
                    type uint32;
                    sros-ext:immutable;
                    description "NAT group (including WLAN Gateway group) that executes the reassembly";
                }

                leaf to-base-network {
                    type boolean;
                    default "false";
                    description "Allow reassembled traffic sent to network interface";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container reassembly

            container sfm-overload {
                presence "Enable the sfm-overload context";
                description "Enable the sfm-overload context";

                leaf holdoff-time {
                    type uint32 {
                        range "1..600";
                    }
                    units "seconds";
                    description "Delay in detecting SFM failures and setting overload";
                }

            } // container sfm-overload

            container confederation {
                when "../router-name = 'Base'" {
                    description "only allowed in the Base router";
                }
                description "Enter the confederation context";

                leaf confed-as-num {
                    type inet:as-number {
                        range "1..4294967295";
                    }
                    description "Confederation AS number";
                }

                list members {
                    key "as-number";
                    max-elements 256;
                    description "Add a list entry for members";

                    leaf as-number {
                        type inet:as-number {
                            range "1..4294967295";
                        }
                        description "Confederation member AS number";
                    }

                } // list members

            } // container confederation

            list interface {
                key "interface-name";
                description "Enter the interface list instance";

                leaf interface-name {
                    type types-sros:interface-name;
                    description "Router interface name";
                }

                leaf flavor {
                    when "not(../../router-name = 'management')" {
                        description "not allowed in the management router";
                    }
                    type enumeration {
                        enum regular {
                            value 0;
                            description "Regular network interface";
                        }
                        enum pdn {
                            value 2;
                            description "PDN interface";
                        }
                        enum unnumbered-mpls-tp {
                            value 3;
                            description "Unnumbered MPLS-TP interface";
                        }
                        enum control-tunnel {
                            status obsolete;
                            description "Creates a network interface of control-tunnel type.";
                        }
                        enum gmpls-loopback {
                            status obsolete;
                            description "Creates a network interface of gmpls-loopback type.";
                        }
                    }
                    sros-ext:immutable;
                    default "regular";
                    description "Network interface flavor";
                }

                leaf cpu-protection {
                    when "../../router-name = 'Base' and not(../flavor = 'pdn')" {
                        description "only allowed in router Base, and not in an interface with flavor pdn";
                    }
                    type leafref {
                        path "../../../system/security/cpu-protection/policy/policy-id";
                    }
                    description "CPU protection policy ID for the interface";
                }

                leaf description {
                    when "not(../../router-name = 'management')" {
                        description "not allowed in the management router";
                    }
                    type types-sros:very-long-description;
                    description "Text description";
                }

                leaf ip-mtu-profile {
                    when "not(../../router-name = 'management') and not(../flavor = 'unnumbered-mpls-tp') and not(../interface-name = 'system')" {
                        description "not allowed in the management router, and not in the system interface nor in an interface with flavor unnumbered-mpls-tp";
                    }
                    type boolean;
                    default "false";
                    description "Enable the interface IP MTU profile";
                }

                leaf ip-mtu {
                    when "not(../../router-name = 'management')" {
                        description "not allowed in the management router";
                    }
                    type types-router:ip-mtu-ext;
                    units "bytes";
                    description "Interface IP MTU";
                }

                leaf admin-state {
                    when "not(../../router-name = 'management')" {
                        description "not allowed in the management router";
                    }
                    type types-sros:admin-state;
                    description "Administrative state of the interface";
                }

                leaf strip-label {
                    when "../../router-name = 'Base' and not(../flavor = 'pdn') and not(../interface-name = 'system')" {
                        description "only allowed in router Base, and not in the system interface nor in an interface with flavor pdn";
                    }
                    type boolean;
                    default "false";
                    description "Strip all MPLS labels before PBR processing";
                }

                leaf dist-cpu-protection {
                    when "../../router-name = 'Base' and not(../flavor = 'pdn') and not(../interface-name = 'system')" {
                        description "only allowed in router Base, and not in the system interface nor in an interface with flavor pdn";
                    }
                    type leafref {
                        path "../../../system/security/dist-cpu-protection/policy/policy-name";
                    }
                    description "DCP policy name for interface";
                }

                leaf mac {
                    when "../../router-name = 'Base' and not(../flavor = 'pdn')" {
                        description "only allowed in router Base, and not in an interface with flavor pdn";
                    }
                    type types-sros:mac-unicast-address;
                    description "MAC address of the interface";
                }

                leaf tos-marking-state {
                    when "../../router-name = 'Base'" {
                        description "only allowed in router Base";
                    }
                    type types-router:tos-marking-state;
                    default "trusted";
                    description "TOS marking state";
                }

                leaf ingress-stats {
                    when "../../router-name = 'Base'" {
                        description "only allowed in router Base";
                    }
                    type boolean;
                    default "false";
                    description "Collect ingress statistics";
                }

                leaf mac-accounting {
                    when "../../router-name = 'Base' and not(../flavor = 'pdn')" {
                        description "only allowed in router Base, and not in an interface with flavor pdn";
                    }
                    type boolean;
                    default "false";
                    description "Enable MAC accounting functionality";
                }

                leaf vas-if-type {
                    when "../../router-name = 'Base' and ../flavor = 'regular' and not(../interface-name = 'system')" {
                        description "only allowed in regular interfaces in router Base, and not in the system interface";
                    }
                    type types-router:vas-if-type;
                    description "Value Added Service (VAS) facing interface type";
                }

                leaf gre-termination {
                    status obsolete;
                    type boolean;
                    default "false";
                    description "Terminate GRE packets on primary subnet of interface";
                }

                leaf urpf-selected-vprns {
                    when "../../router-name = 'Base' and ../flavor = 'regular' and not(../interface-name = 'system')" {
                        description "only allowed in regular interfaces in router Base, and not in the system interface";
                    }
                    type boolean;
                    default "false";
                    description "Enable uRPF checking of incoming traffic on interface";
                }

                leaf accounting-policy {
                    type leafref {
                        path "../../../log/accounting-policy/policy-id";
                    }
                    description "Accounting policy to apply to the router interface";
                }

                leaf collect-stats {
                    type boolean;
                    default "false";
                    description "Enable collection of statistics on the router interface";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice port-binding {
                    case port-encap {

                        leaf port {
                            when "not(../../router-name = 'management') and not(../interface-name = 'system')" {
                                description "not allowed in the management router, and not in the system interface";
                            }
                            type types-router:router-port;
                            description "Port to bind to this interface";
                        }

                    }
                    case loopback {

                        leaf loopback {
                            when "not(../../router-name = 'management') and not(../flavor = 'unnumbered-mpls-tp') and not(../interface-name = 'system')" {
                                description "not allowed in the management router, and not in the system interface nor in an interface with flavor unnumbered-mpls-tp";
                            }
                            type empty;
                            description "Use interface as a loopback interface";
                        }

                    }
                }
                container egress {
                    when "../../router-name = 'Base' and not(../interface-name = 'system')" {
                        description "only allowed in the Base router, not in the system interface or an interface with flavor control-tunnel";
                    }
                    description "Enter the egress context";

                    container filter {
                        description "Enter the filter context";

                        leaf ip {
                            type leafref {
                                path "../../../../../filter/ip-filter/filter-name";
                            }
                            description "IPv4 filter policy name";
                        }

                        leaf ipv6 {
                            type leafref {
                                path "../../../../../filter/ipv6-filter/filter-name";
                            }
                            description "IPv6 filter policy name";
                        }

                    } // container filter

                    container qos {
                        description "Enter the qos context";

                        leaf burst-limit {
                            type types-qos:vlan-qos-burst-limit;
                            description "Maximum traffic burst size for router interface egress";
                        }

                        leaf sink-excess-bw {
                            type boolean;
                            default "false";
                            description "Use virtual flows to sink excess bandwidth";
                        }

                        leaf low-rate {
                            type boolean;
                            default "false";
                            description "Use low-rate scheduling";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice egress-agg-rate {
                            default "agg-rate";
                            case agg-rate {

                                container agg-rate {
                                    description "Enter the agg-rate context";

                                    container rate {
                                        description "Enter the rate context";

                                        leaf pir {
                                            type union {
                                                type int32 {
                                                    range "1..400000000";
                                                }
                                                type enumeration {
                                                    enum max                            { value -1; }
                                                }
                                            }
                                            units "kilobps";
                                            default "max";
                                            description "Administrative PIR";
                                        }

                                        leaf cir {
                                            type union {
                                                type int32 {
                                                    range "0..400000000";
                                                }
                                                type enumeration {
                                                    enum max                            { value -1; }
                                                }
                                            }
                                            units "kilobps";
                                            default "0";
                                            description "Administrative CIR";
                                        }

                                    } // container rate

                                } // container agg-rate

                            }
                            case percent-agg-rate {

                                container percent-agg-rate {
                                    description "Enter the percent-agg-rate context";

                                    leaf pir {
                                        type decimal64 {
                                            range "0.01..100.00";
                                            fraction-digits 2;
                                        }
                                        description "PIR percent rate";
                                    }

                                    leaf cir {
                                        type decimal64 {
                                            range "0.00..100.00";
                                            fraction-digits 2;
                                        }
                                        description "CIR percent rate";
                                    }

                                } // container percent-agg-rate

                            }
                        }
                        container vlan-qos-policy {
                            description "Enter the vlan-qos-policy context";

                            leaf policy-name {
                                type leafref {
                                    path "../../../../../../qos/vlan-qos-policy/vlan-qos-policy-name";
                                }
                                description "VLAN QoS policy name";
                            }

                            leaf port-redirect {
                                type boolean;
                                default "false";
                                description "Enable port-redirect for the egress VLAN QoS policy";
                            }

                        } // container vlan-qos-policy

                        container egress-remark-policy {
                            description "Enter the egress-remark-policy context";

                            leaf policy-name {
                                type leafref {
                                    path "../../../../../../qos/egress-remark-policy/egress-remark-policy-name";
                                }
                                description "Egress remark policy name";
                            }

                        } // container egress-remark-policy

                    } // container qos

                } // container egress

                container ingress {
                    when "../../router-name = 'Base' and not(../interface-name = 'system')" {
                        description "only allowed in router Base, and not in the system interface";
                    }
                    description "Enter the ingress context";

                    leaf policy-accounting {
                        when "not(../../flavor = 'pdn')" {
                            description "not allowed in an interface with flavor pdn";
                        }
                        type leafref {
                            path "../../../../routing-options/policy-accounting/policy-acct-template/name";
                        }
                        description "Policy accounting template applied to the interface";
                    }

                    leaf destination-class-lookup {
                        when "../../flavor = 'regular'" {
                            description "only allowed in regular interfaces in router Base, and not in the system interface";
                        }
                        type boolean;
                        default "false";
                        description "Enable BGP destination class lookup";
                    }

                    leaf ip-filter-pair {
                        type boolean;
                        default "false";
                        description "Enable pairing IPv4 and IPv6 filters";
                    }

                    container filter {
                        description "Enter the filter context";

                        leaf ip {
                            type leafref {
                                path "../../../../../filter/ip-filter/filter-name";
                            }
                            description "IPv4 filter policy name";
                        }

                        leaf ipv6 {
                            type leafref {
                                path "../../../../../filter/ipv6-filter/filter-name";
                            }
                            description "IPv6 filter policy name";
                        }

                    } // container filter

                    container qos {
                        description "Enter the qos context";

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container network-ingress {
                            description "Enter the network-ingress context";

                            leaf policy-name {
                                type leafref {
                                    path "../../../../../../qos/network-ingress/network-ingress-policy-name";
                                }
                                description "Network ingress QoS policy name";
                            }

                        } // container network-ingress

                    } // container qos

                } // container ingress

                container ldp-sync-timer {
                    when "../../router-name = 'Base' and not(../flavor = 'pdn') and not(../interface-name = 'system')" {
                        description "only allowed in router Base, and not in the system interface nor in an interface with flavor pdn";
                    }
                    description "Enter the ldp-sync-timer context";

                    leaf seconds {
                        type types-router:ldp-sync-timer;
                        description "Time interval for the LDP synchronization timer";
                    }

                    leaf end-of-lib {
                        type boolean;
                        default "false";
                        description "Terminate LDP synchronization timer";
                    }

                } // container ldp-sync-timer

                container load-balancing {
                    when "../../router-name = 'Base' and not(../flavor = 'pdn') and not(../interface-name = 'system')" {
                        description "only allowed in router Base, and not in the system interface nor in an interface with flavor pdn";
                    }
                    description "Enter the load-balancing context";

                    leaf lsr-load-balancing {
                        type types-router:lsr-load-balancing;
                        description "LSR load-balancing algorithm";
                    }

                    leaf ip-load-balancing {
                        type types-router:ip-load-balancing;
                        default "both";
                        description "IP load-balancing algorithm";
                    }

                    leaf spi-load-balancing {
                        type boolean;
                        default "false";
                        description "Enable SPI use in hashing";
                    }

                    leaf teid-load-balancing {
                        type boolean;
                        default "false";
                        description "Enable use of TEID in hashing";
                    }

                    leaf flow-label-load-balancing {
                        type boolean;
                        default "false";
                        description "Enable flow label load balancing";
                    }

                } // container load-balancing

                container lag {
                    when "../../router-name = 'Base' and not(../flavor = 'pdn') and not(../interface-name = 'system')" {
                        description "only allowed in router Base, and not in the system interface nor in an interface with flavor pdn";
                    }
                    description "Enter the lag context";

                    leaf link-map-profile {
                        type types-services:link-map-profile-id;
                        description "LAG link map profile for a SAP or network interface";
                    }

                    container per-link-hash {
                        when "not(../../flavor = 'unnumbered-mpls-tp')" {
                            description "not allowed on interfaces with flavor unnumbered-mpls-tp";
                        }
                        description "Enter the per-link-hash context";

                        leaf class {
                            type types-services:sap-lag-per-link-hash-class;
                            default "1";
                            description "Class used on LAG egress using weighted per-link-hash";
                        }

                        leaf weight {
                            type types-services:sap-lag-per-link-hash-weight;
                            default "1";
                            description "Weight used on LAG egress using weighted per-link-hash";
                        }

                    } // container per-link-hash

                } // container lag

                container ptp-hw-assist {
                    when "../../router-name = 'Base'" {
                        description "only allowed in the Base router";
                    }
                    description "Enter the ptp-hw-assist context";

                    leaf admin-state {
                        type types-sros:admin-state;
                        default "disable";
                        description "Administrative state of the PTP timestamping assist";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container ptp-hw-assist

                container urpf-check {
                    when "../../router-name = 'Base' and not(../flavor = 'pdn') and not(../interface-name = 'system')" {
                        description "only allowed in router Base, and not in the system interface nor in an interface with flavor pdn";
                    }
                    presence "Enable the urpf-check context";
                    description "Enable the urpf-check context";

                    leaf ignore-default {
                        type boolean;
                        default "false";
                        description "Ignore default route when performing a uRPF check";
                    }

                    leaf mode {
                        type types-router:urpf-check-mode;
                        default "strict";
                        description "Unicast RPF check mode";
                    }

                } // container urpf-check

                container autoconfigure {
                    description "Enter the autoconfigure context";

                    container ipv4 {
                        when "not(../../../router-name = 'management')" {
                            description "not allowed in the management router";
                        }
                        description "Enter the ipv4 context";

                        container dhcp-client {
                            when "../../../../router-name = 'Base' and not(../../../interface-name = 'system') and not(../../../flavor = 'pdn')" {
                                description "only allowed in router Base, and not in the system interface nor in an interface with flavor pdn";
                            }
                            presence "Enable the dhcp-client context";
                            description "Enable the dhcp-client context";

                            leaf admin-state {
                                type types-sros:admin-state;
                                default "disable";
                                description "Administrative state of the DHCP client";
                            }

                            leaf lease-time {
                                type union {
                                    type types-sros:time-duration {
                                        range "10..315446399";
                                    }
                                    type enumeration {
                                        enum infinite {
                                            value -1;
                                            description "Request an infinite lease with no expiry";
                                        }
                                    }
                                }
                                sros-ext:auto-restart-to-modify;
                                default "86400";
                                description "Lease time the DHCP client requests";
                            }

                            leaf-list apply-groups {
                                type leafref {
                                    path "../../../../../../groups/group/name";
                                }
                                max-elements 8;
                                ordered-by user;
                                sros-ext:auto-restart-to-modify;
                                description "Apply a configuration group at this level";
                            }

                            leaf-list apply-groups-exclude {
                                type leafref {
                                    path "../../../../../../groups/group/name";
                                }
                                max-elements 8;
                                ordered-by user;
                                sros-ext:auto-restart-to-modify;
                                description "Exclude a configuration group at this level";
                            }

                            container class-id {
                                sros-ext:auto-restart-to-modify;
                                description "Enter the class-id context";

                                choice format {
                                    case ascii-string {

                                        leaf ascii-string {
                                            type string {
                                                length "1..127";
                                            }
                                            sros-ext:auto-restart-to-modify;
                                            description "Vendor class ID as an ASCII string";
                                        }

                                    }
                                    case hex-string {

                                        leaf hex-string {
                                            type types-sros:hex-string {
                                                length "1..256";
                                            }
                                            sros-ext:auto-restart-to-modify;
                                            description "Vendor class ID as a hexadecimal string";
                                        }

                                    }
                                }
                            } // container class-id

                            container client-id {
                                sros-ext:auto-restart-to-modify;
                                description "Enter the client-id context";

                                choice format {
                                    case mac {

                                        leaf mac {
                                            type empty;
                                            sros-ext:auto-restart-to-modify;
                                            description "MAC address as the client ID";
                                        }

                                    }
                                    case interface {

                                        leaf interface {
                                            type empty;
                                            sros-ext:auto-restart-to-modify;
                                            description "Interface name as the client ID";
                                        }

                                    }
                                    case ascii-string {

                                        leaf ascii-string {
                                            type string {
                                                length "1..127";
                                            }
                                            sros-ext:auto-restart-to-modify;
                                            description "Client ID as an ASCII string";
                                        }

                                    }
                                    case hex-string {

                                        leaf hex-string {
                                            type types-sros:hex-string {
                                                length "1..256";
                                            }
                                            sros-ext:auto-restart-to-modify;
                                            description "Client ID as a hexadecimal string";
                                        }

                                    }
                                }
                            } // container client-id

                            container request-options {
                                sros-ext:auto-restart-to-modify;
                                description "Enter the request-options context";

                                leaf dns-server {
                                    type boolean;
                                    sros-ext:auto-restart-to-modify;
                                    default "false";
                                    description "Include the DNS server option";
                                }

                                leaf router {
                                    type boolean;
                                    sros-ext:auto-restart-to-modify;
                                    default "false";
                                    description "Include the router option";
                                }

                                leaf static-route {
                                    type boolean;
                                    sros-ext:auto-restart-to-modify;
                                    default "false";
                                    description "Include the static route option";
                                }

                            } // container request-options

                        } // container dhcp-client

                    } // container ipv4

                } // container autoconfigure

                container ipsec {
                    presence "Enable the ipsec context";
                    description "Enable the ipsec context";

                    leaf admin-state {
                        type types-sros:admin-state;
                        default "disable";
                        description "Administrative state of IPsec secured interface";
                    }

                    leaf tunnel-group {
                        type leafref {
                            path "../../../../isa/tunnel-group/id";
                        }
                        sros-ext:immutable;
                        mandatory true;
                        description "Tunnel group ID";
                    }

                    leaf public-sap {
                        type uint32 {
                            range "0..4094";
                        }
                        sros-ext:immutable;
                        mandatory true;
                        description "Public SAP ID";
                    }

                    leaf ip-exception {
                        type leafref {
                            path "../../../../filter/ip-exception/filter-name";
                        }
                        description "IP exception filter";
                    }

                    leaf ipv6-exception {
                        type leafref {
                            path "../../../../filter/ipv6-exception/filter-name";
                        }
                        description "IPv6 filter exception used to bypass encryption";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list ipsec-tunnel {
                        key "name";
                        description "Enter the ipsec-tunnel list instance";

                        leaf name {
                            type types-sros:named-item {
                                pattern "[a-zA-Z]+.*" {
                                    error-message "'name' must not start with a number (e.g. tunnel-1)";
                                }
                            }
                            description "IPsec tunnel name";
                        }

                        leaf private-sap {
                            type uint32 {
                                range "0..4094";
                            }
                            sros-ext:immutable;
                            sros-ext:auto-restart-to-modify;
                            mandatory true;
                            description "Private SAP ID";
                        }

                        leaf admin-state {
                            type types-sros:admin-state;
                            default "disable";
                            description "Administrative state of the IPsec tunnel";
                        }

                        leaf description {
                            type types-sros:description;
                            description "Text description";
                        }

                        leaf clear-df-bit {
                            type boolean;
                            sros-ext:auto-restart-to-modify;
                            default "false";
                            description "Reset the DF bit to 0 in all payload IP packets";
                        }

                        leaf copy-traffic-class-upon-decapsulation {
                            type boolean;
                            sros-ext:auto-restart-to-modify;
                            default "false";
                            description "Enable traffic class copy upon decapsulation";
                        }

                        leaf encapsulated-ip-mtu {
                            type uint32 {
                                range "512..9000";
                            }
                            units "bytes";
                            sros-ext:auto-restart-to-modify;
                            description "Maximum size of the encapsulated tunnel packet";
                        }

                        leaf ip-mtu {
                            type uint32 {
                                range "512..9000";
                            }
                            units "bytes";
                            sros-ext:auto-restart-to-modify;
                            description "Private MTU of the IPsec tunnel";
                        }

                        leaf replay-window {
                            type uint32 {
                                range "32|64|128|256|512";
                            }
                            units "packets";
                            sros-ext:auto-restart-to-modify;
                            description "Anti-replay window size";
                        }

                        leaf public-tcp-mss-adjust {
                            type union {
                                type uint32 {
                                    range "512..9000";
                                }
                                type enumeration {
                                    enum auto                           { value 0; }
                                }
                            }
                            units "bytes";
                            sros-ext:auto-restart-to-modify;
                            description "TCP maximum segment size (MSS) on the public network";
                        }

                        leaf private-tcp-mss-adjust {
                            type int32 {
                                range "512..9000";
                            }
                            units "bytes";
                            sros-ext:auto-restart-to-modify;
                            description "TCP maximum segment size (MSS) adjustment";
                        }

                        leaf local-gateway-address-override {
                            type types-sros:ip-address;
                            sros-ext:auto-restart-to-modify;
                            description "Local IPsec tunnel endpoint address";
                        }

                        leaf remote-gateway-address {
                            type types-sros:ip-address;
                            sros-ext:auto-restart-to-modify;
                            description "Remote IPsec tunnel endpoint address";
                        }

                        leaf private-service {
                            type types-services:service-name;
                            sros-ext:immutable;
                            sros-ext:auto-restart-to-modify;
                            description "Private service name";
                        }

                        leaf propagate-pmtu-v4 {
                            type boolean;
                            sros-ext:auto-restart-to-modify;
                            default "true";
                            description "Enable propagation of the path MTU to IPv4 hosts";
                        }

                        leaf propagate-pmtu-v6 {
                            type boolean;
                            sros-ext:auto-restart-to-modify;
                            default "true";
                            description "Enable propagation of the path MTU to IPv6 hosts";
                        }

                        leaf pmtu-discovery-aging {
                            type uint32 {
                                range "900..3600";
                            }
                            units "seconds";
                            sros-ext:auto-restart-to-modify;
                            default "900";
                            description "Aging out time of the learned path MTU";
                        }

                        leaf-list apply-groups {
                            type leafref {
                                path "../../../../../groups/group/name";
                            }
                            max-elements 8;
                            ordered-by user;
                            sros-ext:auto-restart-to-modify;
                            description "Apply a configuration group at this level";
                        }

                        leaf-list apply-groups-exclude {
                            type leafref {
                                path "../../../../../groups/group/name";
                            }
                            max-elements 8;
                            ordered-by user;
                            sros-ext:auto-restart-to-modify;
                            description "Exclude a configuration group at this level";
                        }

                        container bfd {
                            sros-ext:auto-restart-to-modify;
                            description "Enter the bfd context";

                            leaf bfd-designate {
                                type boolean;
                                sros-ext:auto-restart-to-modify;
                                default "false";
                                description "Designate IPsec tunnel to carry BFD traffic";
                            }

                            container bfd-liveness {
                                presence "Enable the bfd-liveness context";
                                sros-ext:auto-restart-to-modify;
                                description "Enable the bfd-liveness context";

                                leaf dest-ip {
                                    type types-sros:ipv4-unicast-address;
                                    sros-ext:auto-restart-to-modify;
                                    mandatory true;
                                    description "Destination address used for the BFD session";
                                }

                                leaf interface {
                                    type types-sros:interface-name;
                                    sros-ext:auto-restart-to-modify;
                                    mandatory true;
                                    description "Name of the interface used by the BFD session";
                                }

                                leaf service-name {
                                    type types-services:service-name;
                                    sros-ext:auto-restart-to-modify;
                                    mandatory true;
                                    description "Administrative service name";
                                }

                            } // container bfd-liveness

                        } // container bfd

                        container icmp6-generation {
                            sros-ext:auto-restart-to-modify;
                            description "Enter the icmp6-generation context";

                            container packet-too-big {
                                sros-ext:auto-restart-to-modify;
                                description "Enter the packet-too-big context";

                                leaf admin-state {
                                    type types-sros:admin-state;
                                    sros-ext:auto-restart-to-modify;
                                    default "enable";
                                    description "Administrative state of Packet Too Big message sends";
                                }

                                leaf message-count {
                                    type uint32 {
                                        range "10..1000";
                                    }
                                    sros-ext:auto-restart-to-modify;
                                    default "100";
                                    description "Maximum number of ICMPv6 PTB messages that can be sent";
                                }

                                leaf interval {
                                    type uint32 {
                                        range "1..60";
                                    }
                                    units "seconds";
                                    sros-ext:auto-restart-to-modify;
                                    default "10";
                                    description "Interval for sending Packet Too Big messages";
                                }

                            } // container packet-too-big

                        } // container icmp6-generation

                        container key-exchange {
                            sros-ext:auto-restart-to-modify;
                            description "Enter the key-exchange context";

                            choice type {
                                case dynamic {

                                    container dynamic {
                                        presence "Enable the dynamic context";
                                        sros-ext:auto-restart-to-modify;
                                        description "Enable the dynamic context";

                                        leaf ike-policy {
                                            type leafref {
                                                path "../../../../../../../ipsec/ike-policy/id";
                                            }
                                            sros-ext:auto-restart-to-modify;
                                            description "IKE policy ID";
                                        }

                                        leaf-list ipsec-transform {
                                            type leafref {
                                                path "../../../../../../../ipsec/ipsec-transform/id";
                                            }
                                            max-elements 4;
                                            sros-ext:auto-restart-to-modify;
                                            description "IPsec transform IDs used by the dynamic key";
                                        }

                                        leaf auto-establish {
                                            type boolean;
                                            sros-ext:auto-restart-to-modify;
                                            default "false";
                                            description "Attempt to establish a phase 1 exchange automatically";
                                        }

                                        leaf auto-establish-sustain {
                                            type boolean;
                                            sros-ext:auto-restart-to-modify;
                                            default "false";
                                            description "Enable sustain mode for auto-establish tunnels";
                                        }

                                        leaf pre-shared-key {
                                            type types-sros:encrypted-leaf {
                                                length "1..166";
                                            }
                                            sros-ext:auto-restart-to-modify;
                                            description "Pre-shared key for authentication";
                                        }

                                        container cert {
                                            sros-ext:auto-restart-to-modify;
                                            description "Enter the cert context";

                                            leaf cert-profile {
                                                type leafref {
                                                    path "../../../../../../../../ipsec/cert-profile/name";
                                                }
                                                description "Certificate profile name";
                                            }

                                            leaf trust-anchor-profile {
                                                type leafref {
                                                    path "../../../../../../../../ipsec/trust-anchor-profile/name";
                                                }
                                                description "Trust anchor profile name";
                                            }

                                            container status-verify {
                                                sros-ext:auto-restart-to-modify;
                                                description "Enter the status-verify context";

                                                leaf default-result {
                                                    type enumeration {
                                                        enum revoked                        { value 0; }
                                                        enum good                           { value 1; }
                                                    }
                                                    default "revoked";
                                                    description "Default result for Certificate Status Verification";
                                                }

                                                leaf primary {
                                                    type types-ipsec:cert-revocation-status;
                                                    default "crl";
                                                    description "Primary method of CSV to verify the revocation status";
                                                }

                                                leaf secondary {
                                                    type types-ipsec:cert-revocation-status-with-none;
                                                    default "none";
                                                    description "Secondary method used to verify certificate revocation";
                                                }

                                            } // container status-verify

                                        } // container cert

                                        container id {
                                            sros-ext:auto-restart-to-modify;
                                            description "Enter the id context";

                                            choice id {
                                                case ipv4 {

                                                    leaf ipv4 {
                                                        type types-sros:ipv4-unicast-address;
                                                        sros-ext:auto-restart-to-modify;
                                                        description "IPv4 as the local ID type";
                                                    }

                                                }
                                                case ipv6 {

                                                    leaf ipv6 {
                                                        type types-sros:ip-address;
                                                        sros-ext:auto-restart-to-modify;
                                                        description "IPv6 used as the local IKE ID type";
                                                    }

                                                }
                                                case fqdn {

                                                    leaf fqdn {
                                                        type types-sros:fully-qualified-domain-name;
                                                        sros-ext:auto-restart-to-modify;
                                                        description "FQDN used as the local ID IKE type";
                                                    }

                                                }
                                            }
                                        } // container id

                                        container ppk {
                                            sros-ext:auto-restart-to-modify;
                                            description "Enter the ppk context";

                                            leaf list {
                                                type leafref {
                                                    path "../../../../../../../../ipsec/ppk-list/name";
                                                }
                                                sros-ext:auto-restart-to-modify;
                                                description "PPK list instance name";
                                            }

                                            leaf id {
                                                type leafref {
                                                    path "../../../../../../../../ipsec/ppk-list[name=current()/../list]/ppk/ppk-id";
                                                }
                                                sros-ext:auto-restart-to-modify;
                                                description "PPK ID";
                                            }

                                        } // container ppk

                                        container reverse-route-injection {
                                            presence "Enable the reverse-route-injection context";
                                            sros-ext:auto-restart-to-modify;
                                            description "Enable the reverse-route-injection context";

                                            leaf metric {
                                                type uint32 {
                                                    range "0..65535";
                                                }
                                                sros-ext:auto-restart-to-modify;
                                                default "0";
                                                description "Metric to use for reverse route injection";
                                            }

                                            leaf preference {
                                                type uint32 {
                                                    range "0..255";
                                                }
                                                sros-ext:auto-restart-to-modify;
                                                default "0";
                                                description "Preference to use for reverse route injection";
                                            }

                                        } // container reverse-route-injection

                                    } // container dynamic

                                }
                                case manual {

                                    container manual {
                                        presence "Enable the manual context";
                                        sros-ext:auto-restart-to-modify;
                                        description "Enable the manual context";

                                        list keys {
                                            key "security-association direction";
                                            description "Enter the keys list instance";

                                            leaf security-association {
                                                type uint32 {
                                                    range "1..16";
                                                }
                                                description "SA entry ID";
                                            }

                                            leaf direction {
                                                type enumeration {
                                                    enum inbound                        { value 1; }
                                                    enum outbound                       { value 2; }
                                                }
                                                description "Direction of the IPsec tunnel";
                                            }

                                            leaf ipsec-transform {
                                                type leafref {
                                                    path "../../../../../../../../ipsec/ipsec-transform/id";
                                                }
                                                sros-ext:immutable;
                                                mandatory true;
                                                description "Transform entry used by manual SAs";
                                            }

                                            leaf spi {
                                                type uint32 {
                                                    range "256..16383";
                                                }
                                                sros-ext:immutable;
                                                mandatory true;
                                                description "SPI of inbound and outbound packets";
                                            }

                                            leaf authentication-key {
                                                type types-sros:hex-string {
                                                    length "1..130";
                                                }
                                                sros-ext:immutable;
                                                description "Key used for the authentication algorithm";
                                            }

                                            leaf encryption-key {
                                                type types-sros:hex-string {
                                                    length "1..66";
                                                }
                                                sros-ext:immutable;
                                                description "Key used for the encryption algorithm";
                                            }

                                            leaf-list apply-groups {
                                                type leafref {
                                                    path "../../../../../../../../groups/group/name";
                                                }
                                                max-elements 8;
                                                ordered-by user;
                                                description "Apply a configuration group at this level";
                                            }

                                            leaf-list apply-groups-exclude {
                                                type leafref {
                                                    path "../../../../../../../../groups/group/name";
                                                }
                                                max-elements 8;
                                                ordered-by user;
                                                description "Exclude a configuration group at this level";
                                            }

                                        } // list keys

                                    } // container manual

                                }
                            }
                        } // container key-exchange

                        container max-history-key-records {
                            sros-ext:auto-restart-to-modify;
                            description "Enter the max-history-key-records context";

                            leaf ike {
                                type uint32 {
                                    range "1..3";
                                }
                                sros-ext:auto-restart-to-modify;
                                description "Maximum number of historical IKE key records";
                            }

                            leaf esp {
                                type uint32 {
                                    range "1..48";
                                }
                                sros-ext:auto-restart-to-modify;
                                description "Maximum number of recent records";
                            }

                        } // container max-history-key-records

                        container icmp-generation {
                            sros-ext:auto-restart-to-modify;
                            description "Enter the icmp-generation context";

                            container frag-required {
                                sros-ext:auto-restart-to-modify;
                                description "Enter the frag-required context";

                                leaf admin-state {
                                    type types-sros:admin-state;
                                    sros-ext:auto-restart-to-modify;
                                    default "enable";
                                    description "Administrative state of sending ICMP messages";
                                }

                                leaf message-count {
                                    type uint32 {
                                        range "10..1000";
                                    }
                                    sros-ext:auto-restart-to-modify;
                                    default "100";
                                    description "Maximum number of ICMP messages that can be sent";
                                }

                                leaf interval {
                                    type uint32 {
                                        range "1..60";
                                    }
                                    units "seconds";
                                    sros-ext:auto-restart-to-modify;
                                    default "10";
                                    description "Interval for sending ICMP messages";
                                }

                            } // container frag-required

                        } // container icmp-generation


                        container security-policy {
                            sros-ext:auto-restart-to-modify;
                            description "Enter the security-policy context";

                            leaf id {
                                type uint32;
                                sros-ext:auto-restart-to-modify;
                                description "Security policy ID for use by the tunnel";
                            }

                            leaf strict-match {
                                type boolean;
                                sros-ext:auto-restart-to-modify;
                                default "false";
                                description "Enable strict match of the security policy entry";
                            }

                        } // container security-policy

                    } // list ipsec-tunnel

                } // container ipsec

                container cflowd-parameters {
                    when "../../router-name = 'Base'" {
                        description "only allowed in the Base router";
                    }
                    description "Enter the cflowd-parameters context";

                    list sampling {
                        key "sampling-type";
                        description "Enter the sampling list instance";

                        leaf sampling-type {
                            type types-router:cflowd-sampling;
                            description "Traffic sampling type";
                        }

                        leaf type {
                            when "not(../sampling-type = 'both')";
                            type enumeration {
                                enum acl                            { value 1; }
                                enum interface                      { value 2; }
                            }
                            mandatory true;
                            description "Type of cflowd analysis";
                        }

                        leaf direction {
                            type enumeration {
                                enum ingress-only                   { value 1; }
                                enum egress-only                    { value 2; }
                                enum both                           { value 3; }
                            }
                            default "ingress-only";
                            description "Direction of traffic for cflowd sampling";
                        }

                        leaf sample-profile {
                            type union {
                                type enumeration {
                                    enum 1                              { value 1; }
                                }
                                type uint32;
                            }
                            description "Sample profile ID";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list sampling

                } // container cflowd-parameters

                container hold-time {
                    when "../../router-name = 'Base'" {
                        description "only allowed in router Base";
                    }
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                    container ipv6 {
                        when "not(../../flavor = 'pdn')" {
                            description "not allowed in an interface with flavor pdn";
                        }
                        description "Enter the ipv6 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv6

                } // container hold-time

                container eth-cfm {
                    when "../../router-name = 'Base'" {
                        description "only allowed in the Base router";
                    }
                    description "Enter the eth-cfm context";

                    list mep {
                        key "md-admin-name ma-admin-name mep-id";
                        max-elements 1;
                        description "Enter the mep list instance";

                        leaf md-admin-name {
                            type leafref {
                                path "../../../../../eth-cfm/domain/md-admin-name";
                            }
                            description "Maintenance Domain (MD) name";
                        }

                        leaf ma-admin-name {
                            type leafref {
                                path "../../../../../eth-cfm/domain[md-admin-name=current()/../md-admin-name]/association/ma-admin-name";
                            }
                            description "Maintenance Association (MA) name";
                        }

                        leaf mep-id {
                            type types-eth-cfm:mep-id-type;
                            description "Maintenance Endpoint (MEP) ID";
                        }

                        leaf admin-state {
                            type types-sros:admin-state;
                            default "disable";
                            description "Administrative state of the MEP";
                        }

                        leaf description {
                            type types-sros:description;
                            description "Text description";
                        }

                        leaf mac-address {
                            type types-sros:mac-unicast-address-no-zero;
                            description "MAC address of the MEP";
                        }

                        leaf install-mep {
                            type boolean;
                            default "false";
                            description "Install MEP in the forwarding plane";
                        }

                        leaf facility-fault {
                            type boolean;
                            default "false";
                            description "Allow the facility MEP to generate a network action";
                        }

                        leaf ccm {
                            type boolean;
                            default "false";
                            description "Generate CCM messages";
                        }

                        leaf ccm-ltm-priority {
                            type types-eth-cfm:frame-priority;
                            default "7";
                            description "Priority of CCM and LTM messages transmitted by the MEP";
                        }

                        leaf ccm-padding-size {
                            type uint32 {
                                range "3..1500";
                            }
                            description "Number of octets of padding to insert in CCM packets";
                        }

                        leaf-list ccm-tlv-ignore {
                            type types-eth-cfm:ccm-tlv-ignore-type;
                            max-elements 2;
                            description "TLV to ignore on reception";
                        }

                        leaf low-priority-defect {
                            type types-eth-cfm:lowest-alarm-priority;
                            default "mac-rem-err-xcon";
                            description "Lowest priority defect for fault alarm generation";
                        }

                        leaf collect-lmm-stats {
                            type boolean;
                            default "false";
                            description "Collect statistics for loss measurement message tests";
                        }

                        leaf lbm-svc-act-responder {
                            type boolean;
                            description "Process service activation streams in ETH-CFM LBM";
                        }

                        leaf one-way-delay-threshold {
                            type uint32 {
                                range "0..600";
                            }
                            units "seconds";
                            default "3";
                            description "Threshold time limit for the one-way delay test";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container alarm-notification {
                            description "Enter the alarm-notification context";

                            leaf fng-alarm-time {
                                type int32 {
                                    range "250|500|1000";
                                }
                                units "centiseconds";
                                description "Time that must expire before an FNG alarm is raised";
                            }

                            leaf fng-reset-time {
                                type int32 {
                                    range "250|500|1000";
                                }
                                units "centiseconds";
                                description "Time that must expire before an FNG alarm is reset";
                            }

                        } // container alarm-notification

                        container eth-test {
                            presence "Enable the eth-test context";
                            description "Enable the eth-test context";

                            leaf bit-error-threshold {
                                type uint32 {
                                    range "0..11840";
                                }
                                units "bit errors";
                                default "1";
                                description "Lowest priority defect allowed to generate fault alarm";
                            }

                            container test-pattern {
                                description "Enter the test-pattern context";

                                leaf pattern {
                                    type enumeration {
                                        enum all-zeros                      { value 0; }
                                        enum all-ones                       { value 1; }
                                    }
                                    default "all-zeros";
                                    description "Test pattern for Ethernet Test frames";
                                }

                                leaf crc-tlv {
                                    type boolean;
                                    default "false";
                                    description "Generate a CRC checksum";
                                }

                            } // container test-pattern

                        } // container eth-test

                        container collect-lmm-fc-stats {
                            description "Enter the collect-lmm-fc-stats context";

                            leaf-list fc {
                                type types-eth-cfm:fc-type;
                                max-elements 8;
                                description "Forwarding class name for profile-unaware counter";
                            }

                            leaf-list fc-in-profile {
                                type types-eth-cfm:fc-type;
                                max-elements 8;
                                description "Forwarding class name for profile-aware counter";
                            }

                        } // container collect-lmm-fc-stats

                        container grace {
                            description "Enter the grace context";

                            container eth-ed {
                                description "Enter the eth-ed context";

                                leaf max-rx-defect-window {
                                    type uint32 {
                                        range "1..86400";
                                    }
                                    units "seconds";
                                    description "Maximum received ETH-ED expected defect window duration";
                                }

                                leaf priority {
                                    type int32 {
                                        range "0..7";
                                    }
                                    description "Transmission priority for ETH-ED PDUs";
                                }

                                leaf rx-eth-ed {
                                    type boolean;
                                    default "true";
                                    description "Receive and process ETH-ED ITU-T Y.1731 PDUs on the MEP";
                                }

                                leaf tx-eth-ed {
                                    type boolean;
                                    default "false";
                                    description "Transmit ETH-ED PDUs from the MEP";
                                }

                            } // container eth-ed

                            container eth-vsm-grace {
                                description "Enter the eth-vsm-grace context";

                                leaf rx-eth-vsm-grace {
                                    type boolean;
                                    default "true";
                                    description "Receive and process Nokia ETH-CFM Grace PDU on the MEP";
                                }

                                leaf tx-eth-vsm-grace {
                                    type boolean;
                                    default "true";
                                    description "Transmit ETH-ED PDUs from the MEP";
                                }

                            } // container eth-vsm-grace

                        } // container grace

                    } // list mep

                } // container eth-cfm

                container ethernet {
                    description "Enter the ethernet context";

                    container loopback-mode {
                        presence "Enable the loopback-mode context";
                        description "Enable the loopback-mode context";

                        leaf mode {
                            type enumeration {
                                enum line                           { value 0; }
                            }
                            default "line";
                            description "Loopback mode for the associated port or channel";
                        }

                        leaf mac-swap {
                            type boolean;
                            default "false";
                            description "Enable MAC address swapping";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container loopback-mode

                } // container ethernet

                container ipv4 {
                    when "not(../../router-name = 'management')" {
                        description "not allowed in the management router";
                    }
                    description "Enter the ipv4 context";

                    leaf tcp-mss {
                        when "../../../router-name = 'Base' and not(../../flavor = 'pdn')" {
                            description "only allowed in router Base, and not in an interface with flavor pdn";
                        }
                        type types-router:ipv4-tcp-mss-ext;
                        description "TCP maximum segment size for the interface";
                    }

                    leaf allow-directed-broadcasts {
                        when "../../../router-name = 'Base' and not(../../flavor = 'pdn')" {
                            description "only allowed in router Base, and not in an interface with flavor pdn";
                        }
                        type boolean;
                        default "false";
                        description "Forward directed broadcasts";
                    }

                    leaf local-dhcp-server {
                        when "../../../router-name = 'Base' and not(../../flavor = 'pdn')" {
                            description "only allowed in router Base, and not in an interface with flavor pdn";
                        }
                        type leafref {
                            path "../../../dhcp-server/dhcpv4/name";
                        }
                        description "DHCP server for the interface";
                    }

                    leaf qos-route-lookup {
                        when "../../../router-name = 'Base' and not(../../flavor = 'pdn')" {
                            description "only allowed in router Base, and not in an interface with flavor pdn";
                        }
                        type types-router:qos-route-lookup;
                        description "IP address for QoS route lookup for ingress IP packets";
                    }

                    leaf gre-termination {
                        when "../../../router-name = 'Base' and ../../flavor = 'regular' and not(../../interface-name = 'system')" {
                            description "only allowed in regular interfaces in router Base, and not in the system interface";
                        }
                        type boolean;
                        default "false";
                        description "Configure GRE termination in the virtual router for the primary subnet of this interface.";
                    }

                    leaf ip-helper-address {
                        when "../../../router-name = 'Base' and ../../flavor = 'regular' and not(../../interface-name = 'system')" {
                            description "only allowed in regular interfaces in router Base, and not in the system interface";
                        }
                        type types-sros:ipv4-unicast-address;
                        description "IP address of the target UDP broadcast gateway";
                    }

                    container icmp {
                        when "../../../router-name = 'Base'" {
                            description "only allowed in router Base";
                        }
                        description "Enter the icmp context";

                        leaf mask-reply {
                            type boolean;
                            default "true";
                            description "Allow responses to ICMP mask requests on the interface";
                        }

                        container redirects {
                            description "Enter the redirects context";

                            leaf admin-state {
                                type types-sros:admin-state;
                                default "enable";
                                description "Administrative state of sending ICMP redirect messages";
                            }

                            leaf number {
                                type uint16 {
                                    range "10..1000";
                                }
                                default "100";
                                description "Maximum number of ICMP redirect messages to send";
                            }

                            leaf seconds {
                                type uint16 {
                                    range "1..60";
                                }
                                units "seconds";
                                default "10";
                                description "Time used to limit the number of ICMP redirect messages";
                            }

                        } // container redirects

                        container ttl-expired {
                            description "Enter the ttl-expired context";

                            leaf admin-state {
                                type types-sros:admin-state;
                                default "enable";
                                description "Administrative state of sending TTL expired messages";
                            }

                            leaf number {
                                type uint16 {
                                    range "10..2000";
                                }
                                default "100";
                                description "Maximum number of TTL expired messages to send";
                            }

                            leaf seconds {
                                type uint16 {
                                    range "1..60";
                                }
                                units "seconds";
                                default "10";
                                description "Time used to limit the number of TTL expired messages";
                            }

                        } // container ttl-expired

                        container unreachables {
                            description "Enter the unreachables context";

                            leaf admin-state {
                                type types-sros:admin-state;
                                default "enable";
                                description "Administrative state of sending unreachable messages";
                            }

                            leaf number {
                                type uint16 {
                                    range "10..2000";
                                }
                                default "100";
                                description "Maximum number of unreachable messages to send";
                            }

                            leaf seconds {
                                type uint16 {
                                    range "1..60";
                                }
                                units "seconds";
                                default "10";
                                description "Time to limit the number of ICMP unreachable messages";
                            }

                        } // container unreachables

                        container param-problem {
                            description "Enter the param-problem context";

                            leaf admin-state {
                                type types-sros:admin-state;
                                default "enable";
                                description "Administrative state of sent Parameter Problem messages";
                            }

                            leaf number {
                                type uint32 {
                                    range "10..1000";
                                }
                                default "100";
                                description "Maximum number of Parameter Problem messages to send";
                            }

                            leaf seconds {
                                type uint32 {
                                    range "1..60";
                                }
                                units "seconds";
                                default "10";
                                description "Time used to limit number of Parameter Problem messages";
                            }

                        } // container param-problem

                    } // container icmp

                    container unnumbered {
                        when "../../../router-name = 'Base' and not(../../interface-name = 'system')" {
                            description "only allowed in router Base, and not in the system interface";
                        }
                        description "Enter the unnumbered context";

                        choice source {
                            case ip-address {

                                leaf ip-address {
                                    type types-sros:ipv4-unicast-address;
                                    description "IP address to associate with unnumbered IP interface";
                                }

                            }
                            case ip-int-name {

                                leaf ip-int-name {
                                    type types-sros:interface-name;
                                    description "Unnumbered IP interface name";
                                }

                            }
                            case ip-int-system {

                                leaf system {
                                    type empty;
                                    description "Use system IP address for the unnumbered IP interface";
                                }

                            }
                        }
                    } // container unnumbered

                    container urpf-check {
                        when "../../../router-name = 'Base' and not(../../flavor = 'pdn') and not(../../interface-name = 'system')" {
                            description "only allowed in router Base, and not in the system interface nor in an interface with flavor pdn";
                        }
                        presence "Enable the urpf-check context";
                        description "Enable the urpf-check context";

                        leaf ignore-default {
                            type boolean;
                            default "false";
                            description "Ignore default routes when performing a uRPF check";
                        }

                        leaf mode {
                            type types-router:urpf-check-mode;
                            default "strict";
                            description "Unicast RPF check mode";
                        }

                    } // container urpf-check

                    container dhcp {
                        when "../../../router-name = 'Base' and not(../../interface-name = 'system') and not(../../flavor = 'pdn')" {
                            description "only allowed in router Base, and not in the system interface nor in an interface with flavor pdn";
                        }
                        description "Enter the dhcp context";

                        leaf admin-state {
                            type types-sros:admin-state;
                            description "Administrative state of DHCP";
                        }

                        leaf description {
                            type types-sros:description;
                            description "Text description";
                        }

                        leaf python-policy {
                            type leafref {
                                path "../../../../../python/python-policy/name";
                            }
                            description "Python policy name";
                        }

                        leaf-list server {
                            type types-sros:ipv4-unicast-address;
                            max-elements 8;
                            ordered-by user;
                            description "IP addresses for DHCP server requests";
                        }

                        leaf trusted {
                            type boolean;
                            default "false";
                            description "Relay untrusted packets";
                        }

                        leaf gi-address {
                            type types-sros:ipv4-unicast-address;
                            description "GI address for the DHCP relay";
                        }

                        leaf release-include-gi-address {
                            type boolean;
                            default "false";
                            description "Include gateway IP address in DHCP Release messages";
                        }

                        leaf src-ip-addr {
                            type enumeration {
                                enum auto                           { value 0; }
                                enum gi-address                     { value 1; }
                            }
                            default "auto";
                            description "Type of source address to use for DHCP relay";
                        }

                        leaf relay-plain-bootp {
                            type boolean;
                            default "false";
                            description "Relay plain BOOTP messages";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container option-82 {
                            description "Enter the option-82 context";

                            leaf action {
                                type enumeration {
                                    enum replace                        { value 1; }
                                    enum drop                           { value 2; }
                                    enum keep                           { value 3; }
                                }
                                default "keep";
                                description "Action to take with received DHCP Option 82";
                            }

                            container circuit-id {
                                description "Enter the circuit-id context";

                                choice circuit-id {
                                    default "ascii-tuple";
                                    case none {

                                        leaf none {
                                            type empty;
                                            description "Do not include the circuit ID";
                                        }

                                    }
                                    case ifindex {

                                        leaf ifindex {
                                            type empty;
                                            description "Use the interface index for the circuit ID";
                                        }

                                    }
                                    case ascii-tuple {

                                        leaf ascii-tuple {
                                            type empty;
                                            description "Use the ASCII-encoded tuple for the circuit ID";
                                        }

                                    }
                                    case vlan-ascii-tuple {

                                        leaf vlan-ascii-tuple {
                                            type empty;
                                            description "Include the VLAN ID and dot1p bits in the ASCII tuple";
                                        }

                                    }
                                    case port-id {

                                        leaf port-id {
                                            type empty;
                                            description "Use the port ID for the circuit ID";
                                        }

                                    }
                                    case if-name {

                                        leaf if-name {
                                            type empty;
                                            description "Use the interface name for the circuit ID";
                                        }

                                    }
                                }
                            } // container circuit-id

                            container remote-id {
                                description "Enter the remote-id context";

                                choice remote-id {
                                    default "none";
                                    case none {

                                        leaf none {
                                            type empty;
                                            description "Do not include the remote ID";
                                        }

                                    }
                                    case mac {

                                        leaf mac {
                                            type empty;
                                            description "Use the MAC address for the remote ID";
                                        }

                                    }
                                    case ascii-string {

                                        leaf ascii-string {
                                            type types-sros:string-not-all-spaces {
                                                length "1..32";
                                            }
                                            description "User-defined ASCII string for the remote ID";
                                        }

                                    }
                                }
                            } // container remote-id

                            container vendor-specific-option {
                                description "Enter the vendor-specific-option context";

                                leaf system-id {
                                    type boolean;
                                    default "false";
                                    description "Send the system ID in the VSO";
                                }

                                leaf client-mac-address {
                                    type boolean;
                                    default "false";
                                    description "Send the MAC address in the VSO";
                                }

                                leaf pool-name {
                                    type boolean;
                                    default "false";
                                    description "Send the pool name in the VSO";
                                }

                                leaf port-id {
                                    type boolean;
                                    default "false";
                                    description "Send the port ID in the VSO";
                                }

                                leaf service-id {
                                    type boolean;
                                    default "false";
                                    description "Send the service ID in the Vendor Specific Option";
                                }

                                leaf string {
                                    type types-sros:string-not-all-spaces {
                                        length "1..32";
                                    }
                                    description "User-defined ASCII string for the VSO";
                                }

                            } // container vendor-specific-option

                        } // container option-82

                    } // container dhcp

                    container bfd {
                        when "../../../router-name = 'Base'" {
                            description "only allowed in the Base router";
                        }
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "Transmit interval";
                        }

                        leaf receive {
                            type uint32 {
                                range "10..100000";
                            }
                            units "milliseconds";
                            default "100";
                            description "Receive interval";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum cpm-np {
                                    value 1;
                                    description "Terminate on the CPM network processor";
                                }
                                enum auto {
                                    value 2;
                                    description "Terminate on the system-selected termination point";
                                }
                                enum fp {
                                    value 3;
                                    description "Terminate on the forwarding plane";
                                }
                            }
                            default "auto";
                            description "Local termination point for the BFD session";
                        }

                        leaf padded-size {
                            type uint32 {
                                range "0|52..1512";
                            }
                            units "bytes";
                            default "0";
                            description "BFD payload padded size";
                        }

                    } // container bfd

                    container primary {
                        when "not(../../../router-name = 'management') and not(../../flavor = 'pdn') and not(../../flavor = 'unnumbered-mpls-tp')" {
                            description "not allowed in an interface with flavor pdn|unnumbered-mpls-tp";
                        }
                        presence "Enable the primary context";
                        description "Enable the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf broadcast {
                            when "../../../../router-name = 'Base'" {
                                description "only allowed in the Base router";
                            }
                            type types-services:broadcast-address-format;
                            default "host-ones";
                            description "Broadcast address format";
                        }

                        leaf track-srrp {
                            when "../../../../router-name = 'Base' and ../../../flavor = 'regular'" {
                                description "only allowed in regular interfaces in router Base";
                            }
                            type uint32 {
                                range "1..4294967295";
                            }
                            description "SRRP instance whose state is tracked on this IP address";
                        }

                        leaf tag {
                            when "../../../../router-name = 'Base' and ../../../flavor = 'regular'" {
                                description "only allowed in regular interfaces in router Base";
                            }
                            type union {
                                type uint32 {
                                    range "1..4294967295";
                                }
                                type enumeration {
                                    enum no-tag                         { value 0; }
                                }
                            }
                            default "no-tag";
                            description "Route tag to be matched by BGP export policy rules";
                        }

                        leaf gre-termination {
                            when "../../../../router-name = 'Base' and ../../../flavor = 'regular' and not(../../../interface-name = 'system')" {
                                description "only allowed in regular interfaces in router Base, and not in the system interface";
                            }
                            type boolean;
                            default "false";
                            description "Enable GRE termination";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container primary

                    list secondary {
                        when "../../../router-name = 'Base' and ../../flavor = 'regular' and not(../../interface-name = 'system')" {
                            description "only allowed in regular interfaces in router Base, and not in the system interface";
                        }
                        key "address";
                        description "Enter the secondary list instance";

                        leaf address {
                            type types-sros:ipv4-unicast-address;
                            description "Secondary IPv4 address assigned to the interface";
                        }

                        leaf prefix-length {
                            type uint32 {
                                range "0..32";
                            }
                            mandatory true;
                            description "IPv4 address prefix length";
                        }

                        leaf igp-inhibit {
                            type boolean;
                            default "false";
                            description "Disable the running IGP from recognizing secondary IP";
                        }

                        leaf broadcast {
                            when "../../../../router-name = 'Base'" {
                                description "only allowed in the Base router";
                            }
                            type types-services:broadcast-address-format;
                            default "host-ones";
                            description "Broadcast address format";
                        }

                        leaf track-srrp {
                            when "../../../../router-name = 'Base' and ../../../flavor = 'regular'" {
                                description "only allowed in regular interfaces in router Base";
                            }
                            type uint32 {
                                range "1..4294967295";
                            }
                            description "SRRP instance whose state is tracked on this IP address";
                        }

                        leaf tag {
                            when "../../../../router-name = 'Base' and ../../../flavor = 'regular'" {
                                description "only allowed in regular interfaces in router Base";
                            }
                            type union {
                                type uint32 {
                                    range "1..4294967295";
                                }
                                type enumeration {
                                    enum no-tag                         { value 0; }
                                }
                            }
                            default "no-tag";
                            description "Route tag to be matched by BGP export policy rules";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list secondary

                    container nat {
                        presence "Enable the nat context";
                        description "Enable the nat context";

                        leaf cpm-nat-policy {
                            type leafref {
                                path "../../../../../service/nat/cpm-nat-policy/name";
                            }
                            description "CPM NAT policy association with public IPv4 interface";
                        }

                        leaf cpm-spf-nat-policy {
                            type leafref {
                                path "../../../../../service/nat/cpm-nat-policy/name";
                            }
                            description "CPM NAT policy for static port forwards";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container nat

                    container neighbor-discovery {
                        when "not(../../interface-name = 'system') and not(../../flavor = 'pdn')" {
                            description "not allowed in the system interface nor in an interface with flavor pdn";
                        }
                        description "Enter the neighbor-discovery context";

                        leaf timeout {
                            when "../../../../router-name = 'Base'" {
                                description "only allowed in the Base router";
                            }
                            type uint32 {
                                range "0..65535";
                            }
                            units "seconds";
                            default "14400";
                            description "Timeout for an ARP entry learned on the interface";
                        }

                        leaf retry-timer {
                            when "../../../../router-name = 'Base'" {
                                description "only allowed in the Base router";
                            }
                            type uint32 {
                                range "1..300";
                            }
                            units "deciseconds";
                            default "50";
                            description "ARP retry interval";
                        }

                        leaf learn-unsolicited {
                            when "../../../../router-name = 'Base'" {
                                description "only allowed in the Base router";
                            }
                            type boolean;
                            default "false";
                            description "Learn new entries from any received NA message";
                        }

                        leaf proactive-refresh {
                            when "../../../../router-name = 'Base'" {
                                description "only allowed in the Base router";
                            }
                            type boolean;
                            default "false";
                            description "Send a single refresh message before entry timeout";
                        }

                        leaf local-proxy-arp {
                            when "../../../../router-name = 'Base'" {
                                description "only allowed in the Base router";
                            }
                            type boolean;
                            description "Enable local proxy ARP on interface";
                        }

                        leaf remote-proxy-arp {
                            when "../../../../router-name = 'Base'" {
                                description "only allowed in the Base router";
                            }
                            type boolean;
                            default "false";
                            description "Enable remote proxy ARP on the interface";
                        }

                        leaf-list proxy-arp-policy {
                            when "../../../../router-name = 'Base'" {
                                description "only allowed in the Base router";
                            }
                            type leafref {
                                path "../../../../../policy-options/policy-statement/name";
                            }
                            max-elements 5;
                            ordered-by user;
                            description "Proxy ARP policy name";
                        }

                        container limit {
                            when "../../../../router-name = 'Base'" {
                                description "only allowed in the Base router";
                            }
                            description "Enter the limit context";

                            leaf max-entries {
                                type types-router:ipv4-neighbor-limit;
                                description "Maximum number of entries learned on an IP interface";
                            }

                            leaf log-only {
                                type boolean;
                                default "false";
                                description "Generate log entries only if limit is reached";
                            }

                            leaf threshold {
                                type uint32 {
                                    range "1..100";
                                }
                                units "percent";
                                default "90";
                                description "Threshold value that triggers a warning message";
                            }

                        } // container limit

                        container host-route {
                            description "Enter the host-route context";

                            list populate {
                                key "route-type";
                                description "Enter the populate list instance";

                                leaf route-type {
                                    type enumeration {
                                        enum static {
                                            value 1;
                                            description "Host routes created from EVPN ARP or ND entries";
                                        }
                                        enum dynamic {
                                            value 2;
                                            description "Host routes created from dynamic ARP or ND entries";
                                        }
                                        enum evpn {
                                            value 3;
                                            description "Host routes created from EVPN entries";
                                        }
                                        enum evpn-local-es {
                                            value 4;
                                            description "Host routes created from EVPN local ES entries";
                                        }
                                    }
                                    description "Type of ARP or ND entries that generate host routes";
                                }

                                leaf route-tag {
                                    type uint32 {
                                        range "1..255";
                                    }
                                    sros-ext:immutable;
                                    description "Tag value used with the host route from an ARP/ND entry";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                            } // list populate

                        } // container host-route

                        container static-neighbor-unnumbered {
                            when "../../../../router-name = 'Base'" {
                                description "only allowed in router Base";
                            }
                            presence "Enable the static-neighbor-unnumbered context";
                            description "Enable the static-neighbor-unnumbered context";

                            leaf mac-address {
                                type yang:mac-address;
                                sros-ext:auto-restart-to-modify;
                                mandatory true;
                                description "MAC address for the static neighbor";
                            }

                        } // container static-neighbor-unnumbered

                        list static-neighbor {
                            when "../../../../router-name = 'Base'" {
                                description "only allowed in router Base";
                            }
                            key "ipv4-address";
                            description "Enter the static-neighbor list instance";

                            leaf ipv4-address {
                                type types-sros:ipv4-address;
                                description "IPv4 address that corresponds to the physical address";
                            }

                            leaf mac-address {
                                type yang:mac-address;
                                mandatory true;
                                description "MAC address for the static neighbor";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list static-neighbor

                    } // container neighbor-discovery

                    list vrrp {
                        when "../../../router-name = 'Base' and not(../../interface-name = 'system')" {
                            description "only allowed in the Base router, and not in the system interface";
                        }
                        key "virtual-router-id";
                        description "Enter the vrrp list instance";

                        leaf virtual-router-id {
                            type int32 {
                                range "1..255";
                            }
                            description "Virtual Router Identifier (VRID) for the IP interface";
                        }

                        leaf authentication-key {
                            type types-sros:encrypted-leaf {
                                length "1..94";
                            }
                            description "Password for simple text authentication";
                        }

                        leaf-list backup {
                            type types-sros:ipv4-unicast-address;
                            max-elements 16;
                            description "Virtual router IP addresses for the interface";
                        }

                        leaf message-interval {
                            type uint32 {
                                range "1..2559";
                            }
                            units "deciseconds";
                            default "10";
                            description "Interval for sending VRRP advertisement messages";
                        }

                        leaf owner {
                            type boolean;
                            sros-ext:immutable;
                            default "false";
                            description "Designate the virtual router instance as owner";
                        }

                        leaf passive {
                            type boolean;
                            sros-ext:immutable;
                            default "false";
                            description "Suppress the processing of VRRP advertisement messages";
                        }

                        leaf init-delay {
                            type uint32 {
                                range "1..65535";
                            }
                            units "seconds";
                            description "VRRP initialization delay timer";
                        }

                        leaf mac {
                            type types-sros:mac-unicast-address;
                            description "Virtual MAC address to use in ARP responses";
                        }

                        leaf priority {
                            type uint32 {
                                range "1..255";
                            }
                            description "Base priority for the VRRP";
                        }

                        leaf admin-state {
                            type types-sros:admin-state;
                            default "enable";
                            description "Administrative state of VRRP";
                        }

                        leaf master-int-inherit {
                            type boolean;
                            description "Allow master instance to dictate the master down timer";
                        }

                        leaf ping-reply {
                            type boolean;
                            default "false";
                            description "Allow non-owner master to reply to ICMP echo requests";
                        }

                        leaf policy {
                            type leafref {
                                path "../../../../../vrrp/policy/policy-id";
                            }
                            description "VRRP priority control policy";
                        }

                        leaf preempt {
                            type boolean;
                            default "true";
                            description "Allow the VRRP to override an existing non-owner master";
                        }

                        leaf telnet-reply {
                            type boolean;
                            default "false";
                            description "Allow non-owner master to reply to Telnet requests";
                        }

                        leaf traceroute-reply {
                            type boolean;
                            default "false";
                            description "Allow non-owner master to reply to traceroute requests";
                        }

                        leaf standby-forwarding {
                            type boolean;
                            default "false";
                            description "Allow standby router to forward traffic";
                        }

                        leaf ssh-reply {
                            type boolean;
                            default "false";
                            description "Allow the non-owner master to reply to SSH requests";
                        }

                        leaf ntp-reply {
                            type boolean;
                            default "false";
                            description "Allow processing of NTP requests";
                        }

                        leaf oper-group {
                            type leafref {
                                path "../../../../../service/oper-group/name";
                            }
                            description "Operational group name associated with the VRRP";
                        }

                        leaf monitor-oper-group {
                            type leafref {
                                path "../../../../../service/oper-group/name";
                            }
                            sros-ext:immutable;
                            description "VRRP instance to follow a specified operational group";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container bfd-liveness {
                            presence "Enable the bfd-liveness context";
                            description "Enable the bfd-liveness context";

                            leaf dest-ip {
                                type types-sros:ipv4-address;
                                sros-ext:immutable;
                                mandatory true;
                                description "Destination IP address to use for BFD session";
                            }

                            leaf service-name {
                                type types-services:service-name;
                                sros-ext:immutable;
                                description "Administrative service name";
                            }

                            leaf interface-name {
                                type types-sros:interface-name;
                                sros-ext:immutable;
                                mandatory true;
                                description "Name of the interface running BFD";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // container bfd-liveness

                    } // list vrrp

                } // container ipv4

                container ipv6 {
                    when "../../router-name = 'Base'" {
                        description "only allowed in router Base";
                    }
                    presence "Enable the ipv6 context";
                    description "Enable the ipv6 context";

                    leaf qos-route-lookup {
                        when "../../../router-name = 'Base' and not(../../flavor = 'pdn')" {
                            description "only allowed in router Base, and not in an interface with flavor pdn";
                        }
                        type types-router:qos-route-lookup;
                        description "IP address for QoS route lookup for ingress IP packets";
                    }

                    leaf forward-ipv4-packets {
                        when "../../../router-name = 'Base' and ../../flavor = 'regular' and not(../../interface-name = 'system')" {
                            description "only allowed in regular interfaces in router Base, and not in the system interface";
                        }
                        type boolean;
                        default "false";
                        description "Forward unencapsulated IPv4 packets";
                    }

                    leaf tcp-mss {
                        when "../../../router-name = 'Base' and not(../../flavor = 'pdn')" {
                            description "only allowed in router Base, and not in an interface with flavor pdn";
                        }
                        type types-router:ipv6-tcp-mss-ext;
                        description "TCP maximum segment size for the IPv6 interface";
                    }

                    leaf duplicate-address-detection {
                        when "../../../router-name = 'Base'" {
                            description "only allowed in the Base router";
                        }
                        type boolean;
                        default "true";
                        description "Enable Duplicate Address Detection";
                    }

                    leaf gre-termination {
                        when "../../../router-name = 'Base' and ../../flavor = 'regular' and not(../../interface-name = 'system')" {
                            description "only allowed in regular interfaces in router Base, and not in the system interface";
                        }
                        type boolean;
                        default "false";
                        description "Enable IPv6 GRE termination on a loopback interface";
                    }

                    leaf local-dhcp-server {
                        type leafref {
                            path "../../../dhcp-server/dhcpv6/name";
                        }
                        description "DHCP server for the interface";
                    }

                    container icmp6 {
                        description "Enter the icmp6 context";

                        container packet-too-big {
                            description "Enter the packet-too-big context";

                            leaf admin-state {
                                type types-sros:admin-state;
                                default "enable";
                                description "Administrative state of Packet Too Big message sends";
                            }

                            leaf number {
                                type uint16 {
                                    range "10..1000";
                                }
                                default "100";
                                description "Number of Packet Too big Messages issued per time frame";
                            }

                            leaf seconds {
                                type uint16 {
                                    range "1..60";
                                }
                                default "10";
                                description "Time used to limit Packet Too Big messages";
                            }

                        } // container packet-too-big

                        container param-problem {
                            description "Enter the param-problem context";

                            leaf admin-state {
                                type types-sros:admin-state;
                                default "enable";
                                description "Administrative state of Parameter Problem message sends";
                            }

                            leaf number {
                                type uint16 {
                                    range "10..1000";
                                }
                                default "100";
                                description "Number used to limit ICMPv6 Parameter Problem messages";
                            }

                            leaf seconds {
                                type uint16 {
                                    range "1..60";
                                }
                                default "10";
                                description "Time used to limit ICMPv6 Parameter Problem messages";
                            }

                        } // container param-problem

                        container redirects {
                            description "Enter the redirects context";

                            leaf admin-state {
                                type types-sros:admin-state;
                                default "enable";
                                description "Administrative state of Redirect message sends";
                            }

                            leaf number {
                                type uint16 {
                                    range "10..1000";
                                }
                                default "100";
                                description "Number to limit ICMPv6 Redirect messages per time frame";
                            }

                            leaf seconds {
                                type uint16 {
                                    range "1..60";
                                }
                                default "10";
                                description "Time used to limit ICMPv6 Redirect messages";
                            }

                        } // container redirects

                        container time-exceeded {
                            description "Enter the time-exceeded context";

                            leaf admin-state {
                                type types-sros:admin-state;
                                default "enable";
                                description "Administrative state of Time Exceeded message sends";
                            }

                            leaf number {
                                type uint16 {
                                    range "10..2000";
                                }
                                default "100";
                                description "Number to limit Time Exceeded messages per time frame";
                            }

                            leaf seconds {
                                type uint16 {
                                    range "1..60";
                                }
                                default "10";
                                description "Time used to limit ICMPv6 Time Exceeded messages";
                            }

                        } // container time-exceeded

                        container unreachables {
                            description "Enter the unreachables context";

                            leaf admin-state {
                                type types-sros:admin-state;
                                default "enable";
                                description "Administrative state of Unreachable message sends";
                            }

                            leaf number {
                                type uint16 {
                                    range "10..2000";
                                }
                                default "100";
                                description "Number to limit Unreachable messages per time frame";
                            }

                            leaf seconds {
                                type uint16 {
                                    range "1..60";
                                }
                                default "10";
                                description "Time used to limit ICMPv6 Unreachable messages";
                            }

                        } // container unreachables

                    } // container icmp6

                    container link-local-address {
                        when "not(../../interface-name = 'system')" {
                            description "not allowed on the system interface";
                        }
                        description "Enter the link-local-address context";

                        leaf address {
                            type types-sros:ipv6-address;
                            description "IPv6 link-local address";
                        }

                        leaf duplicate-address-detection {
                            type boolean;
                            default "true";
                            description "Enable Duplicate Address Detection";
                        }

                    } // container link-local-address

                    container urpf-check {
                        when "../../../router-name = 'Base' and not(../../flavor = 'pdn') and not(../../interface-name = 'system')" {
                            description "only allowed in router Base, and not in the system interface nor in an interface with flavor pdn";
                        }
                        presence "Enable the urpf-check context";
                        description "Enable the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "Transmit interval";
                        }

                        leaf receive {
                            type uint32 {
                                range "10..100000";
                            }
                            units "milliseconds";
                            default "100";
                            description "Receive interval";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum cpm-np {
                                    value 1;
                                    description "Terminate on the CPM network processor";
                                }
                                enum auto {
                                    value 2;
                                    description "Terminate on the system-selected termination point";
                                }
                                enum fp {
                                    value 3;
                                    description "Terminate on the forwarding plane";
                                }
                            }
                            default "auto";
                            description "Local termination point for the BFD session";
                        }

                        leaf padded-size {
                            type uint32 {
                                range "0|52..1512";
                            }
                            units "bytes";
                            default "0";
                            description "BFD payload padded size";
                        }

                    } // container bfd

                    list address {
                        key "ipv6-address";
                        description "Enter the address list instance";

                        leaf ipv6-address {
                            type types-sros:ipv6-address;
                            description "IPv6 address assigned to the interface";
                        }

                        leaf prefix-length {
                            type uint32 {
                                range "4..128";
                            }
                            mandatory true;
                            description "IPv6 address prefix length";
                        }

                        leaf eui-64 {
                            type boolean;
                            sros-ext:immutable;
                            default "false";
                            description "Form IPv6 address from prefix and 64-bit interface ID";
                        }

                        leaf duplicate-address-detection {
                            type boolean;
                            sros-ext:immutable;
                            default "true";
                            description "Enable Duplicate Address Detection";
                        }

                        leaf primary-preference {
                            type uint32 {
                                range "1..4294967295";
                            }
                            description "Index assigned to the IPv6 address of the interface";
                        }

                        leaf track-srrp {
                            type uint32 {
                                range "1..4294967295";
                            }
                            description "SRRP ID whose state is tracked on this IP address";
                        }

                        leaf tag {
                            type union {
                                type uint32 {
                                    range "1..4294967295";
                                }
                                type enumeration {
                                    enum no-tag                         { value 0; }
                                }
                            }
                            default "no-tag";
                            description "Route tag to be matched by BGP export policy rules";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list address

                    container neighbor-discovery {
                        when "not(../../interface-name = 'system') and not(../../flavor = 'pdn')" {
                            description "not allowed in the system interface, and not in an interface with flavor pdn";
                        }
                        description "Enter the neighbor-discovery context";

                        leaf reachable-time {
                            type types-router:neighbor-discovery-reachable-time;
                            description "Neighbor reachability detection timer";
                        }

                        leaf stale-time {
                            type types-router:neighbor-discovery-stale-time;
                            description "Time a Neighbor Discovery cache entry remains stale";
                        }

                        leaf learn-unsolicited {
                            type types-router:ipv6-address-type-selection;
                            description "Type of entries learned from unsolicited NA messages";
                        }

                        leaf proactive-refresh {
                            type types-router:ipv6-address-type-selection;
                            description "Proactive refresh of neighbor entries";
                        }

                        leaf local-proxy-nd {
                            type boolean;
                            default "false";
                            description "Enable local proxy neighbor discovery on the interface";
                        }

                        leaf-list proxy-nd-policy {
                            type leafref {
                                path "../../../../../policy-options/policy-statement/name";
                            }
                            max-elements 5;
                            ordered-by user;
                            description "Proxy Neighbor Discovery policy name for the interface";
                        }

                        container host-route {
                            description "Enter the host-route context";

                            list populate {
                                key "route-type";
                                description "Enter the populate list instance";

                                leaf route-type {
                                    type enumeration {
                                        enum static {
                                            value 1;
                                            description "Host routes created from EVPN ARP or ND entries";
                                        }
                                        enum dynamic {
                                            value 2;
                                            description "Host routes created from dynamic ARP or ND entries";
                                        }
                                        enum evpn {
                                            value 3;
                                            description "Host routes created from EVPN entries";
                                        }
                                        enum evpn-local-es {
                                            value 4;
                                            description "Host routes created from EVPN local ES entries";
                                        }
                                    }
                                    description "Type of ARP or ND entries that generate host routes";
                                }

                                leaf route-tag {
                                    type uint32 {
                                        range "1..255";
                                    }
                                    sros-ext:immutable;
                                    description "Tag value used with the host route from an ARP/ND entry";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                            } // list populate

                        } // container host-route

                        container secure-nd {
                            description "Enter the secure-nd context";

                            leaf allow-unsecured-msgs {
                                type boolean;
                                default "true";
                                description "Accept unsecured messages";
                            }

                            leaf public-key-min-bits {
                                type uint32 {
                                    range "512..1024";
                                }
                                default "1024";
                                description "Minimum acceptable key length for public keys in CGA";
                            }

                            leaf security-parameter {
                                type uint32 {
                                    range "0..1";
                                }
                                default "1";
                                description "Security parameter used in the generation of a CGA";
                            }

                            leaf admin-state {
                                type types-sros:admin-state;
                                default "disable";
                                description "Administrative state of Secure Neighbor Discovery";
                            }

                        } // container secure-nd

                        container limit {
                            description "Enter the limit context";

                            leaf max-entries {
                                type types-router:ipv6-neighbor-limit;
                                description "Maximum number of entries learned on an IP interface";
                            }

                            leaf log-only {
                                type boolean;
                                default "false";
                                description "Generate log entries when limit is reached";
                            }

                            leaf threshold {
                                type uint32 {
                                    range "1..100";
                                }
                                units "percent";
                                default "90";
                                description "Threshold percentage that triggers a warning message";
                            }

                        } // container limit

                        list static-neighbor {
                            key "ipv6-address";
                            description "Enter the static-neighbor list instance";

                            leaf ipv6-address {
                                type types-sros:ipv6-address;
                                description "IPv6 address corresponding to the physical address";
                            }

                            leaf mac-address {
                                type yang:mac-address;
                                mandatory true;
                                description "MAC address for the static neighbor";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list static-neighbor

                    } // container neighbor-discovery

                    list vrrp {
                        when "../../../router-name = 'Base' and not(../../interface-name = 'system')" {
                            description "only allowed in the Base router, and not in the system interface";
                        }
                        key "virtual-router-id";
                        max-elements 4;
                        description "Enter the vrrp list instance";

                        leaf virtual-router-id {
                            type int32 {
                                range "1..255";
                            }
                            description "Virtual Router Identifier (VRID) for the IP interface";
                        }

                        leaf-list backup {
                            type types-sros:ipv6-address;
                            description "Virtual router IP addresses for the interface";
                        }

                        leaf message-interval {
                            type uint32 {
                                range "10..4095";
                            }
                            units "centiseconds";
                            default "100";
                            description "Interval for sending VRRP advertisement messages";
                        }

                        leaf owner {
                            type boolean;
                            sros-ext:immutable;
                            default "false";
                            description "Designate the virtual router instance as owner";
                        }

                        leaf passive {
                            type boolean;
                            sros-ext:immutable;
                            default "false";
                            description "Suppress the processing of VRRP advertisement messages";
                        }

                        leaf init-delay {
                            type uint32 {
                                range "1..65535";
                            }
                            units "seconds";
                            description "VRRP initialization delay timer";
                        }

                        leaf mac {
                            type types-sros:mac-unicast-address;
                            description "Virtual MAC address to use in ARP responses";
                        }

                        leaf priority {
                            type uint32 {
                                range "1..255";
                            }
                            description "Base priority for the VRRP";
                        }

                        leaf admin-state {
                            type types-sros:admin-state;
                            default "enable";
                            description "Administrative state of VRRP";
                        }

                        leaf master-int-inherit {
                            type boolean;
                            description "Allow master instance to dictate the master down timer";
                        }

                        leaf ping-reply {
                            type boolean;
                            default "false";
                            description "Allow non-owner master to reply to ICMP echo requests";
                        }

                        leaf policy {
                            type leafref {
                                path "../../../../../vrrp/policy/policy-id";
                            }
                            description "VRRP priority control policy";
                        }

                        leaf preempt {
                            type boolean;
                            default "true";
                            description "Allow the VRRP to override an existing non-owner master";
                        }

                        leaf telnet-reply {
                            type boolean;
                            default "false";
                            description "Allow non-owner master to reply to Telnet requests";
                        }

                        leaf traceroute-reply {
                            type boolean;
                            default "false";
                            description "Allow non-owner master to reply to traceroute requests";
                        }

                        leaf standby-forwarding {
                            type boolean;
                            default "false";
                            description "Allow standby router to forward traffic";
                        }

                        leaf ntp-reply {
                            type boolean;
                            default "false";
                            description "Allow processing of NTP requests";
                        }

                        leaf oper-group {
                            type leafref {
                                path "../../../../../service/oper-group/name";
                            }
                            description "Operational group name associated with the VRRP";
                        }

                        leaf monitor-oper-group {
                            type leafref {
                                path "../../../../../service/oper-group/name";
                            }
                            sros-ext:immutable;
                            description "VRRP instance to follow a specified operational group";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container bfd-liveness {
                            presence "Enable the bfd-liveness context";
                            description "Enable the bfd-liveness context";

                            leaf dest-ip {
                                type types-sros:ip-address;
                                sros-ext:immutable;
                                mandatory true;
                                description "Destination address for the BFD session";
                            }

                            leaf service-name {
                                type types-services:service-name;
                                sros-ext:immutable;
                                description "Administrative service name";
                            }

                            leaf interface-name {
                                type types-sros:interface-name;
                                sros-ext:immutable;
                                mandatory true;
                                description "Name of the interface running BFD";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // container bfd-liveness

                    } // list vrrp

                } // container ipv6

                container ip-tunnel {
                    status obsolete;
                    description "Enter the ip-tunnel context";

                    leaf remote-ip {
                        status obsolete;
                        type types-sros:ipv4-unicast-address;
                        description "IP address of the remote end of the IP tunnel";
                    }

                } // container ip-tunnel

                container qos {
                    description "Enter the qos context";

                    leaf network-policy {
                        type leafref {
                            path "../../../../qos/network/network-policy-name";
                        }
                        description "Network policy name associated with a network interface";
                    }

                    leaf egress-port-redirect-group {
                        type leafref {
                            path "../../../../qos/queue-group-templates/egress/queue-group/egress-queue-group-name";
                        }
                        description "QoS queue group name";
                    }

                    leaf egress-instance {
                        type types-services:qos-qgrp-instance-id;
                        description "Port egress queue group instance for this interface";
                    }

                    leaf ingress-fp-redirect-group {
                        type leafref {
                            path "../../../../qos/queue-group-templates/ingress/queue-group/ingress-queue-group-name";
                        }
                        description "Forwarding plane queue group policy for the interface";
                    }

                    leaf ingress-instance {
                        type types-services:qos-qgrp-instance-id;
                        description "Forwarding plane ingress queue group for this interface";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container qos

                container if-attribute {
                    when "../../router-name = 'Base' and not(../flavor = 'unnumbered-mpls-tp')" {
                        description "only allowed in router Base, and not in an interface with flavor unnumbered-mpls-tp";
                    }
                    description "Enter the if-attribute context";

                    leaf-list admin-group {
                        type leafref {
                            path "../../../../routing-options/if-attribute/admin-group/group-name";
                        }
                        max-elements 32;
                        description "Administrative group name for the interface";
                    }

                    list srlg-group {
                        key "name";
                        description "Add a list entry for srlg-group";

                        leaf name {
                            type leafref {
                                path "../../../../../routing-options/if-attribute/srlg-group/name";
                            }
                            description "SRLG name";
                        }

                    } // list srlg-group

                    container delay {
                        description "Enter the delay context";

                        leaf delay-selection {
                            when "not(../../../interface-name = 'system')" {
                                description "Not modifiable on this interface.";
                            }
                            type enumeration {
                                enum static                         { value 1; }
                                enum dynamic                        { value 2; }
                                enum static-preferred               { value 3; }
                                enum dynamic-preferred              { value 4; }
                            }
                            default "static-preferred";
                            description "Delay source advertised by IGP for the interface";
                        }

                        leaf static {
                            type int32 {
                                range "1..16777214";
                            }
                            units "microseconds";
                            description "Unidirectional link delay static information";
                        }

                        container dynamic {
                            when "not(../../../interface-name = 'system')" {
                                description "Not modifiable on this interface.";
                            }
                            description "Enter the dynamic context";

                            leaf measurement-template {
                                status obsolete;
                                type leafref {
                                    path "../../../../../../test-oam/link-measurement/measurement-template/template-name";
                                }
                                description "Link delay measurement template for the interface";
                            }

                            container lag-ip-measurement {
                                description "Enter the lag-ip-measurement context";

                                leaf lag-ip-measurement-template {
                                    type leafref {
                                        path "../../../../../../../test-oam/lag-ip-measurement/lag-ip-measurement-template/template-name";
                                    }
                                    description "LAG IP measurement template for the interface";
                                }

                            } // container lag-ip-measurement

                            container link-measurement {
                                description "Enter the link-measurement context";

                                leaf lag-micro-sessions {
                                    type boolean;
                                    default "false";
                                    description "Use LAG micro sessions on this interface";
                                }

                                leaf link-measurement-template {
                                    type leafref {
                                        path "../../../../../../../test-oam/link-measurement/measurement-template/template-name";
                                    }
                                    description "Link measurement template name";
                                }

                            } // container link-measurement

                            container twamp-light {
                                description "Enter the twamp-light context";

                                container ipv4 {
                                    description "Enter the ipv4 context";

                                    leaf admin-state {
                                        type types-sros:admin-state;
                                        default "disable";
                                        description "Administrative state of IPv4 TWAMP Light packets";
                                    }

                                    leaf destination {
                                        type types-sros:ipv4-unicast-address;
                                        description "TWAMP Light measurement packet destination IPv4 address";
                                    }

                                    leaf source {
                                        type types-sros:ipv4-unicast-address;
                                        description "TWAMP Light measurement packets source IPv4 address";
                                    }

                                } // container ipv4

                                container ipv6 {
                                    description "Enter the ipv6 context";

                                    leaf admin-state {
                                        type types-sros:admin-state;
                                        default "disable";
                                        description "Administrative state of IPv6 TWAMP Light packets";
                                    }

                                    leaf destination {
                                        type types-sros:ipv6-unicast-or-linklocal-address;
                                        description "TWAMP Light measurement packet destination IPv6 address";
                                    }

                                    leaf source {
                                        type types-sros:ipv6-unicast-or-linklocal-address;
                                        description "TWAMP Light measurement packets source IPv6 address";
                                    }

                                } // container ipv6

                            } // container twamp-light

                        } // container dynamic

                    } // container delay

                } // container if-attribute

                container untrusted {
                    when "../../router-name = 'Base' and ../flavor = 'regular' and not(../interface-name = 'system')" {
                        description "only allowed in regular interfaces in router Base, and not in the system interface";
                    }
                    presence "Enable the untrusted context";
                    description "Enable the untrusted context";

                    leaf default-forwarding {
                        type types-router:selective-ilm-default-forwarding;
                        default "forward";
                        description "Default action for selective ILM";
                    }

                } // container untrusted

                container network-domains {
                    when "../../router-name = 'Base'" {
                        description "only allowed in the Base router";
                    }
                    description "Enter the network-domains context";

                    list network-domain {
                        key "domain-name";
                        max-elements 5;
                        description "Add a list entry for network-domain";

                        leaf domain-name {
                            type leafref {
                                path "../../../../network-domains/network-domain/domain-name";
                            }
                            description "Network domain name";
                        }

                    } // list network-domain

                } // container network-domains

                container external-reference {
                    description "Enter the external-reference context";

                    container openconfig {
                        description "Enter the openconfig context";

                        leaf subinterface {
                            type int64 {
                                range "0..4294967295";
                            }
                            description "Reference to the subinterface";
                        }

                    } // container openconfig

                } // container external-reference

            } // list interface

            container ipv6 {
                description "Enter the ipv6 context";

                container neighbor-discovery {
                    when "../../router-name = 'Base'" {
                        description "only allowed in the Base router";
                    }
                    description "Enter the neighbor-discovery context";

                    leaf reachable-time {
                        type types-router:neighbor-discovery-reachable-time;
                        default "30";
                        description "Neighbor reachability detection timer";
                    }

                    leaf stale-time {
                        type types-router:neighbor-discovery-stale-time;
                        default "14400";
                        description "Neighbor discovery cache entry stale time";
                    }

                } // container neighbor-discovery

                container router-advertisement {
                    when "../../router-name = 'Base'" {
                        description "only allowed in the Base router";
                    }
                    description "Enter the router-advertisement context";

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container dns-options {
                        presence "Enable the dns-options context";
                        description "Enable the dns-options context";

                        leaf rdnss-lifetime {
                            type union {
                                type enumeration {
                                    enum infinite                       { value -1; }
                                }
                                type int32 {
                                    range "0|4..3600";
                                }
                            }
                            units "seconds";
                            default "infinite";
                            description "Maximum time over which the RDNSS address is valid";
                        }

                        leaf-list server {
                            type types-sros:ipv6-address;
                            max-elements 4;
                            ordered-by user;
                            description "RAs that are forwarded to IPv6 DNS servers";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container dns-options

                    list interface {
                        key "ip-int-name";
                        description "Enter the interface list instance";

                        leaf ip-int-name {
                            type types-sros:interface-name;
                            description "Router interface name";
                        }

                        leaf current-hop-limit {
                            type uint16 {
                                range "0..255";
                            }
                            default "64";
                            description "Hop limit advertised in RA messages";
                        }

                        leaf managed-configuration {
                            type boolean;
                            default "false";
                            description "Set the managed address configuration flag";
                        }

                        leaf max-advertisement-interval {
                            type uint32 {
                                range "4..1800";
                            }
                            units "seconds";
                            default "600";
                            description "Maximum time between sending advertisement messages";
                        }

                        leaf min-advertisement-interval {
                            type uint32 {
                                range "3..1350";
                            }
                            units "seconds";
                            default "200";
                            description "Minimum interval between router advertisement messages";
                        }

                        leaf mtu {
                            type uint32 {
                                range "1280..9800";
                            }
                            description "MTU for sending packets to the router";
                        }

                        leaf nd-router-preference {
                            type types-router:neighbor-discovery-router-preference;
                            default "medium";
                            description "Default router preference for Router Advertisements";
                        }

                        leaf other-stateful-configuration {
                            type boolean;
                            default "false";
                            description "Set the other configuration flag";
                        }

                        leaf reachable-time {
                            type uint32 {
                                range "0..3600000";
                            }
                            units "milliseconds";
                            default "0";
                            description "Time the router is reachable by other hosts or nodes";
                        }

                        leaf retransmit-time {
                            type uint32 {
                                range "0..1800000";
                            }
                            units "milliseconds";
                            default "0";
                            description "Time to advertise neighbor advertisement messages";
                        }

                        leaf router-lifetime {
                            type uint32 {
                                range "0|4..9000";
                            }
                            units "seconds";
                            default "1800";
                            description "Lifetime value in neighbor advertisement messages";
                        }

                        leaf admin-state {
                            type types-sros:admin-state;
                            default "disable";
                            description "Administrative state of router advertisement";
                        }

                        leaf use-virtual-mac {
                            type boolean;
                            default "false";
                            description "Use VRRP virtual MAC address for advertisement message";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container dns-options {
                            presence "Enable the dns-options context";
                            description "Enable the dns-options context";

                            leaf include-rdnss {
                                type boolean;
                                default "true";
                                description "Include the RDNSS option in the RA";
                            }

                            leaf rdnss-lifetime {
                                type union {
                                    type int32 {
                                        range "0|4..3600";
                                    }
                                    type enumeration {
                                        enum infinite                       { value -1; }
                                    }
                                }
                                units "seconds";
                                description "Maximum time over which the RDNSS address 25 is valid";
                            }

                            leaf-list server {
                                type types-sros:ipv6-address;
                                max-elements 4;
                                ordered-by user;
                                description "RAs that are forwarded to IPv6 DNS servers";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // container dns-options

                        list prefix {
                            key "ipv6-prefix";
                            max-elements 254;
                            description "Enter the prefix list instance";

                            leaf ipv6-prefix {
                                type types-sros:ipv6-prefix;
                                description "IPv6 address prefix";
                            }

                            leaf autonomous {
                                type boolean;
                                default "true";
                                description "Set the autonomous flag value";
                            }

                            leaf on-link {
                                type boolean;
                                default "true";
                                description "Use prefix for on-link determination";
                            }

                            leaf preferred-lifetime {
                                type union {
                                    type enumeration {
                                        enum infinite                       { value -1; }
                                    }
                                    type uint32 {
                                        range "0..4294967294";
                                    }
                                }
                                units "seconds";
                                default "604800";
                                description "Remaining time that the prefix remains preferred";
                            }

                            leaf valid-lifetime {
                                type union {
                                    type enumeration {
                                        enum infinite                       { value -1; }
                                    }
                                    type uint32 {
                                        range "0..4294967294";
                                    }
                                }
                                units "seconds";
                                default "2592000";
                                description "Remaining time in which the prefix is still valid";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list prefix

                    } // list interface

                } // container router-advertisement

            } // container ipv6

            container isa-service-chaining {
                presence "Enable the isa-service-chaining context";
                description "Enable the isa-service-chaining context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list nat-group {
                    key "id";
                    description "Add a list entry for nat-group";

                    leaf id {
                        type uint32;
                        description "ISA NAT group/ISA WLAN GW group ID for the EVPN pools";
                    }

                } // list nat-group

                container vxlan-vtep-range {
                    presence "Enable the vxlan-vtep-range context";
                    description "Enable the vxlan-vtep-range context";

                    leaf start {
                        type types-sros:ip-unicast-without-local-address;
                        mandatory true;
                        description "Start address of the VXLAN VTEP range";
                    }

                    leaf end {
                        type types-sros:ip-unicast-without-local-address;
                        mandatory true;
                        description "End address of the VXLAN VTEP range";
                    }

                } // container vxlan-vtep-range

            } // container isa-service-chaining

            container mpls-labels {
                when "../router-name = 'Base'" {
                    description "only allowed in the Base router";
                }
                description "Enter the mpls-labels context";

                leaf bgp-labels-hold-timer {
                    type uint32 {
                        range "0..255";
                    }
                    default "0";
                    description "BGP labels hold timer for the ingress router";
                }

                leaf static-label-range {
                    type uint32 {
                        range "0..1048544";
                    }
                    default "18400";
                    description "Static label range on the ingress router";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container sr-labels {
                    description "Enter the sr-labels context";

                    leaf start {
                        type types-sros:mpls-label;
                        description "Lower bound of the label range";
                    }

                    leaf end {
                        type types-sros:mpls-label;
                        description "Upper bound of the label range";
                    }

                } // container sr-labels

                list reserved-label-block {
                    key "label-block-name";
                    max-elements 16;
                    description "Enter the reserved-label-block list instance";

                    leaf start-label {
                        type uint32 {
                            range "32..1048575";
                        }
                        description "Lower bound of the reserved label block range";
                    }

                    leaf end-label {
                        type uint32 {
                            range "32..1048575";
                        }
                        description "Upper bound of the reserved label block range";
                    }

                    leaf label-block-name {
                        type types-sros:named-item-64;
                        description "Name for the reserved label block";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list reserved-label-block

            } // container mpls-labels

            container mtrace2 {
                description "Enter the mtrace2 context";

                leaf admin-state {
                    type types-sros:admin-state;
                    default "disable";
                    description "Administrative state of multicast path tracing";
                }

                leaf udp-port {
                    type uint32 {
                        range "1024..49151";
                    }
                    default "5000";
                    description "Destination and listening port for the mtrace2 command";
                }

            } // container mtrace2

            container sgt-qos {
                description "Enter the sgt-qos context";

                container dscp {
                    description "Enter the dscp context";

                    list application {
                        key "dscp-app-name";
                        description "Enter the application list instance";

                        leaf dscp-app-name {
                            type types-router:dscp-app-name;
                            description "DSCP application identifier on the NOKIA SR OS router that generates control traffic over IP";
                        }

                        leaf dscp {
                            type union {
                                type types-qos:dscp-name;
                                type int32 {
                                    range "0..63";
                                }
                            }
                            description "DSCP value to the traffic generated by this application";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list application

                    list dscp-map {
                        when "../../../router-name = 'Base'" {
                            description "only allowed in the Base router";
                        }
                        key "dscp-name";
                        description "Enter the dscp-map list instance";

                        leaf dscp-name {
                            type types-qos:dscp-name;
                            description "DSCP name mapped to forwarding class";
                        }

                        leaf fc {
                            type types-sros:fc-name;
                            description "Value for the forwarding class for this mapping";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list dscp-map

                } // container dscp

                container dot1p {
                    description "Enter the dot1p context";

                    list application {
                        key "dot1p-app-name";
                        description "Enter the application list instance";

                        leaf dot1p-app-name {
                            type types-router:dot1p-app-name;
                            description "Dot1p application ID that generates control traffic";
                        }

                        leaf dot1p {
                            type union {
                                type types-sros:fc-name;
                                type int32 {
                                    range "0..7";
                                }
                            }
                            description "Dot1p value to the traffic generated by this application";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list application

                } // container dot1p

            } // container sgt-qos

            container tunnel-interface {
                when "../router-name = 'Base'" {
                    description "only allowed in the Base router";
                }
                description "Enter the tunnel-interface context";

                list rsvp-p2mp-root {
                    key "lsp-name";
                    description "Enter the rsvp-p2mp-root list instance";

                    leaf lsp-name {
                        type types-sros:named-item;
                        description "LSP name of the P2MP RSVP tunnel interface";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list rsvp-p2mp-root

                list rsvp-p2mp-leaf {
                    key "lsp-name sender-address";
                    description "Enter the rsvp-p2mp-leaf list instance";

                    leaf lsp-name {
                        type types-sros:named-item;
                        description "LSP name of the P2MP RSVP tunnel interface";
                    }

                    leaf sender-address {
                        type types-sros:ipv4-unicast-address;
                        description "Address of a sender for the P2MP RSVP tunnel interface instance";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list rsvp-p2mp-leaf

                list ldp-p2mp-root {
                    key "p2mp-id sender-address";
                    description "Enter the ldp-p2mp-root list instance";

                    leaf p2mp-id {
                        type uint32 {
                            range "1..8192";
                        }
                        description "Identifier used for signaling MLDP P2MP LSP";
                    }

                    leaf sender-address {
                        type types-sros:ipv4-unicast-address;
                        description "Address of an LDP sender for the P2MP RSVP tunnel interface instance";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ldp-p2mp-root

                list ldp-p2mp-leaf {
                    key "p2mp-id sender-address";
                    description "Enter the ldp-p2mp-leaf list instance";

                    leaf p2mp-id {
                        type uint32;
                        description "Identifier used for signaling MLDP P2MP LSP";
                    }

                    leaf sender-address {
                        type types-sros:ipv4-unicast-address;
                        description "Address of an LDP sender for the P2MP RSVP tunnel interface instance";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ldp-p2mp-leaf

            } // container tunnel-interface

            container lsp-bfd {
                when "../router-name = 'Base'" {
                    description "only allowed in the Base router";
                }
                description "Enter the lsp-bfd context";

                leaf bfd-sessions {
                    type uint32 {
                        range "1..max";
                    }
                    description "Maximum number of LSP BFD session tail-ends";
                }

                container tail-end {
                    description "Enter the tail-end context";

                    leaf transmit-interval {
                        type uint32 {
                            range "100..1000";
                        }
                        units "milliseconds";
                        default "1000";
                        description "BFD transmit interval for LSP tail-end";
                    }

                    leaf receive-interval {
                        type uint32 {
                            range "100..1000";
                        }
                        units "milliseconds";
                        default "1000";
                        description "BFD receive interval for LSP tail-end";
                    }

                    leaf multiplier {
                        type uint32 {
                            range "1..20";
                        }
                        default "3";
                        description "Missed message threshold before session is set to down";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container tail-end

            } // container lsp-bfd

            container ttl-propagate {
                when "../router-name = 'Base'" {
                    description "only allowed in the Base router";
                }
                description "Enter the ttl-propagate context";

                leaf label-route-local {
                    type types-router:ttl-propagate-type;
                    default "none";
                    description "TTL propagation from IP header into label stack for local packets";
                }

                leaf label-route-transit {
                    type types-router:ttl-propagate-type;
                    default "none";
                    description "TTL propagation from IP header into label stack for transit packets";
                }

                leaf lsr-label-route {
                    type types-router:ttl-propagate-type;
                    default "none";
                    description "TTL propagation from IP header into label stack";
                }

                leaf sr-mpls-local {
                    type types-router:ttl-propagate-type;
                    default "all";
                    description "TTL propagation for local CPM generated IP packets";
                }

                leaf sr-mpls-transit {
                    type types-router:ttl-propagate-type;
                    default "all";
                    description "TTL propagation for in-transit user IP packets";
                }

                leaf vprn-local {
                    type types-router:router-vprn-ttl-propagate;
                    default "vc-only";
                    description "TTL propagation from IP header into label stack for VPRN local packets";
                }

                leaf vprn-transit {
                    type types-router:router-vprn-ttl-propagate;
                    default "vc-only";
                    description "TTL propagation from IP header into label stack for VPRN transit packets";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container ttl-propagate

            container flowspec {
                when "../router-name = 'Base'" {
                    description "only allowed in the Base router";
                }
                description "Enter the flowspec context";

                leaf ip-filter-max-size {
                    type uint32 {
                        range "0..262143";
                    }
                    default "512";
                    description "Maximum number of FlowSpec rule entries in IPv4 filter";
                }

                leaf ipv6-filter-max-size {
                    type uint32 {
                        range "0..262143";
                    }
                    default "512";
                    description "Maximum number of flowspec rule entries in IPv6 filter";
                }

                leaf filter-cam-type {
                    type enumeration {
                        enum normal                         { value 0; }
                        enum packet-length                  { value 2; }
                    }
                    default "normal";
                    description "Filter policy type for FlowSpec embedding";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container flowspec

            container pcp {
                when "../router-name = 'Base'" {
                    description "only allowed in the Base router";
                }
                description "Enter the pcp context";

                list server {
                    key "name";
                    max-elements 8;
                    description "Enter the server list instance";

                    leaf name {
                        type types-sros:named-item;
                        description "PCP server name";
                    }

                    leaf admin-state {
                        type types-sros:admin-state;
                        default "disable";
                        description "Administrative state of the PCP server";
                    }

                    leaf description {
                        type types-sros:description;
                        description "Text description";
                    }

                    leaf dual-stack-lite-address {
                        type types-sros:ipv6-unicast-address;
                        description "Inside Dual Stack Lite AFTR address";
                    }

                    leaf fwd-inside-router {
                        type string;
                        description "PCP forwarding inside virtual router instance";
                    }

                    leaf policy {
                        type leafref {
                            path "../../../../service/nat/pcp-server-policy/name";
                        }
                        description "PCP server policy";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list interface {
                        key "name";
                        max-elements 32;
                        description "Add a list entry for interface";

                        leaf name {
                            type leafref {
                                path "../../../../interface/interface-name";
                            }
                            description "Interface name";
                        }

                    } // list interface

                } // list server

            } // container pcp

            container network-domains {
                when "../router-name = 'Base'" {
                    description "only allowed in the Base router";
                }
                description "Enter the network-domains context";

                list network-domain {
                    key "domain-name";
                    max-elements 5;
                    description "Enter the network-domain list instance";

                    leaf domain-name {
                        type types-sros:named-item;
                        description "Network domain name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list network-domain

            } // container network-domains

            container ipsec {
                description "Enter the ipsec context";

                list security-policy {
                    key "id";
                    description "Enter the security-policy list instance";

                    leaf id {
                        type uint32 {
                            range "1..32768";
                        }
                        description "IPsec security policy ID";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "entry-id";
                        description "Enter the entry list instance";

                        leaf entry-id {
                            type uint32 {
                                range "1..32";
                            }
                            description "IPsec security policy entry ID";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container local-ip {
                            description "Enter the local-ip context";

                            choice any-or-ip {
                                default "any";
                                case any {

                                    leaf any {
                                        type boolean;
                                        default "false";
                                        description "Use any IP address";
                                    }

                                }
                                case ip {

                                    leaf address {
                                        type types-sros:ipv4-prefix;
                                        description "Destination IPv4 address of the aggregate route";
                                    }

                                }
                            }
                        } // container local-ip

                        container local-ipv6 {
                            description "Enter the local-ipv6 context";

                            choice any-or-ip {
                                default "any";
                                case any {

                                    leaf any {
                                        type boolean;
                                        default "false";
                                        description "Use any IP address";
                                    }

                                }
                                case ip {

                                    leaf address {
                                        type types-sros:ipv6-prefix;
                                        description "Destination IPv6 address of the aggregate route";
                                    }

                                }
                            }
                        } // container local-ipv6

                        container remote-ip {
                            description "Enter the remote-ip context";

                            choice any-or-ip {
                                default "any";
                                case any {

                                    leaf any {
                                        type boolean;
                                        default "false";
                                        description "Use any IP address";
                                    }

                                }
                                case ip {

                                    leaf address {
                                        type types-sros:ipv4-prefix;
                                        description "Destination IPv4 address of the aggregate route";
                                    }

                                }
                            }
                        } // container remote-ip

                        container remote-ipv6 {
                            description "Enter the remote-ipv6 context";

                            choice any-or-ip {
                                default "any";
                                case any {

                                    leaf any {
                                        type boolean;
                                        default "false";
                                        description "Use any IP address";
                                    }

                                }
                                case ip {

                                    leaf address {
                                        type types-sros:ipv6-prefix;
                                        description "Destination IPv6 address of the aggregate route";
                                    }

                                }
                            }
                        } // container remote-ipv6

                    } // list entry

                } // list security-policy

                list multi-chassis-shunt-interface {
                    key "name";
                    description "Enter the multi-chassis-shunt-interface list instance";

                    leaf name {
                        type types-sros:interface-name;
                        description "Multi-chassis shunt interface name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container next-hop {
                        description "Enter the next-hop context";

                        leaf address {
                            type types-sros:ip-unicast-address;
                            description "Next hop address for the shunting interface";
                        }

                    } // container next-hop

                } // list multi-chassis-shunt-interface

                list multi-chassis-shunting-profile {
                    key "name";
                    max-elements 64;
                    description "Enter the multi-chassis-shunting-profile list instance";

                    leaf name {
                        type types-sros:named-item;
                        description "Multi-chassis shunting profile name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list peer {
                        key "ip-address";
                        max-elements 3;
                        description "Enter the peer list instance";

                        leaf ip-address {
                            type leafref {
                                path "../../../../../redundancy/multi-chassis/peer/ip-address";
                            }
                            description "Peer address";
                        }

                        leaf multi-chassis-shunt-interface {
                            type leafref {
                                path "../../../../../router/ipsec/multi-chassis-shunt-interface/name";
                            }
                            description "Multi-chassis shunt interface";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list peer

                } // list multi-chassis-shunting-profile

            } // container ipsec

            container subscriber-mgmt {
                when "../router-name = 'Base'" {
                    description "only allowed in the Base router";
                }
                description "Enter the subscriber-mgmt context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container dhcpv4 {
                    description "Enter the dhcpv4 context";

                    leaf routed-subnet-transparent-forward {
                        type boolean;
                        default "false";
                        description "Transparently forward DHCPv4 from CPE LAN over IPoE";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container dhcpv4

            } // container subscriber-mgmt


            uses conf-router-bgp;
            uses conf-router-bier;
            uses conf-router-dhcp-server;
            uses conf-router-firewall;
            uses conf-router-gtm;
            uses conf-router-igmp;
            uses conf-router-isis;
            uses conf-router-l2tp;
            uses conf-router-ldp;
            uses conf-router-mld;
            uses conf-router-mpls;
            uses conf-router-msdp;
            uses conf-router-nat;
            uses conf-router-origin-validation;
            uses conf-router-ospf;
            uses conf-router-ospf3;
            uses conf-router-p2mp-sr-tree;
            uses conf-router-pcep;
            uses conf-router-pim;
            uses conf-router-radius;
            uses conf-router-rib-api;
            uses conf-router-rip;
            uses conf-router-ripng;
            uses conf-router-rsvp;
            uses conf-router-segment-routing;
            uses conf-router-static-route-static-routes;
            uses conf-router-twamp-light;
            uses conf-router-wpp;
        } // list router

    } // grouping conf-router

}
