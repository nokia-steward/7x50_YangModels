submodule nokia-state-chassis {

    yang-version "1.1";

    belongs-to nokia-state { prefix "state"; }

    import ietf-yang-types                { prefix "yang"; }
    import nokia-sros-yang-extensions     { prefix "sros-ext"; }
    import nokia-types-chassis            { prefix "types-chassis"; }
    import nokia-types-sros               { prefix "types-sros"; }
    import nokia-types-system             { prefix "types-system"; }

    sros-ext:sros-major-release "rel26";
    organization "Nokia";
    contact
        "Nokia SR OS Support
         Web: <http://www.nokia.com>";
    description
        "Nokia YANG Data model with operational state for Physical Chassis related parameters on SR OS based routers.

         Copyright 2016 Nokia. All rights reserved. Reproduction of this document
         is authorized on the condition that the foregoing copyright notice is included.

         This nokia-state-chassis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping state-chassis {
        list chassis {
            key "chassis-class chassis-number";
            description "Enter the chassis list instance";

            leaf chassis-class {
                type types-chassis:chassis-class;
                description "The general purpose functional use of the physical chassis.";
            }

            leaf chassis-number {
                type uint32 {
                    range "1..100";
                }
                description "The unique index identifying this physical chassis.";
            }

            leaf name {
                type types-sros:named-item;
                description "The name for the physical chassis.";
            }

            leaf role {
                type enumeration {
                    enum standalone                     { value 1; }
                    enum master                         { value 2; }
                    enum extension                      { value 3; }
                    enum ethernet-satellite             { value 6; }
                    enum power-shelf                    { value 10; }
                    enum tdm-satellite                  { status obsolete; }
                }
                description
                    "The role in which the physical chassis performs while
                     in the system.";
            }

            leaf state {
                type types-system:device-state;
                description "The device state of the physical chassis.";
            }

            leaf power-supplies {
                type uint32;
                description
                    "The total number of power supplies that can be installed in this
                     physical chassis.";
            }

            leaf fan-trays {
                type uint32;
                description
                    "The total number of fan trays installed in this
                     physical chassis.";
            }

            leaf filter-door-state {
                type enumeration {
                    enum unknown                        { value 0; }
                    enum not-monitored                  { value 1; }
                    enum closed                         { value 2; }
                    enum open                           { value 3; }
                }
                description
                    "The value of filter-door-state indicates the state of
                     the filter door.";
            }

            container hardware-data {
                description "Enter the hardware-data context";

                leaf part-number {
                    type string {
                        length "0..32";
                    }
                    description "Indicates the part number information.";
                }

                leaf serial-number {
                    type string {
                        length "0..32";
                    }
                    description "Indicates the serial number of the hardware component.";
                }

                leaf manufacturing-date {
                    type string {
                        length "0..8";
                    }
                    description "Indicates the manufacturing date of the hardware component.";
                }

                leaf common-language-equipment-identifier {
                    type string {
                        length "0..10";
                    }
                    description
                        "Indicates the CLEI, a unique 10-character identifier fixed
                         by the manufacturer.";
                }

                leaf field-replaceable-unit {
                    type boolean;
                    description
                        "Indicates whether the hardware component is a field
                         replaceable unit or not.";
                }

                leaf oper-state {
                    type types-chassis:hw-oper-state;
                    description "Indicates the operational status of the hardware component.";
                }

                leaf failure-reason {
                    type string {
                        length "0..255";
                    }
                    description
                        "Indicates the reason why a hardware component 'failed' as
                         indicated in oper-state.";
                }

                leaf contains-temperature-sensor {
                    type boolean;
                    description
                        "Indicates whether or not this hardware component contains
                         a temperature sensor.";
                }

                leaf temperature {
                    type int32;
                    description
                        "Indicates the current temperature in degrees celsius from
                         the temperature sensor.";
                }

                leaf temperature-threshold {
                    type int32;
                    description
                        "Indicates the temperature threshold for this hardware
                         component in degrees celsius.";
                }

                leaf over-temperature-status {
                    type enumeration {
                        enum ok                             { value 1; }
                        enum over-temp                      { value 2; }
                    }
                    description
                        "Indicates whether the temperature of the hardware component has exceeded
                         its threshold. If that temperature has been exceeded, a value of
                         'over-temp' (2) will be reported.";
                }

                leaf alarm-state {
                    type enumeration {
                        enum unknown                        { value 0; }
                        enum alarm-active                   { value 1; }
                        enum alarm-cleared                  { value 2; }
                    }
                    description
                        "Indicates the current alarm state for this hardware
                         component.";
                }

                leaf manufacturing-deviations {
                    type string {
                        length "0..255";
                    }
                    description
                        "Indicates the record of changes done by the manfacturing
                         to the hardware or software which is outside the normal
                         revision control process.";
                }

                leaf equipped-platform-type {
                    type types-chassis:equipped-platform-type;
                    description
                        "Indicates the platform type of the installed hardware
                         component, as read from the EEPROM.";
                }

                leaf manufacturing-assembly-number {
                    type string {
                        length "0..32";
                    }
                    description
                        "Indicates an assembly number indicating manufacturing
                         differences for a given part number.";
                }

                leaf power-zone-location {
                    type uint32 {
                        range "0..32";
                    }
                    description
                        "Indicates the managed power zone that this hardware
                         component resides.";
                }

                leaf base-mac-address {
                    type yang:mac-address;
                    description "Indicates the base MAC address of the hardware component.";
                }

                leaf boot-code-version {
                    type string {
                        length "0..255";
                    }
                    description "Indicates the version number of boot eprom.";
                }

                leaf software-code-version {
                    type string {
                        length "0..255";
                    }
                    description
                        "Indicates the software product release version number for the
                         software image currently running.";
                }

                leaf software-last-boot-time {
                    type yang:date-and-time;
                    description
                        "This indicates the date and time the software running on this
                         hardware component was last rebooted.";
                }

            } // container hardware-data

            list chassis-control-module {
                key "ccm-slot";
                description "Enter the chassis-control-module list instance";

                leaf ccm-slot {
                    type string {
                        length "1";
                    }
                    description "The unique value which identifies this CCM slot.";
                }

                leaf equipped-type {
                    type enumeration {
                        enum unknown                        { value 1; }
                        enum ccm-x20                        { value 6; }
                        enum ccm-x16                        { value 7; }
                        enum ccm-e                          { value 8; }
                        enum ccm-1                          { value 9; }
                        enum ccm-1s                         { value 10; }
                        enum ccm-2s                         { value 11; }
                        enum ccm2-x20                       { value 12; }
                    }
                    description "Indicates the CCM type that is equipped.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description
                            "Indicates the CLEI, a unique 10-character identifier fixed
                             by the manufacturer.";
                    }

                    leaf field-replaceable-unit {
                        type boolean;
                        description
                            "Indicates whether the hardware component is a field
                             replaceable unit or not.";
                    }

                    leaf oper-state {
                        type types-chassis:hw-oper-state;
                        description "Indicates the operational status of the hardware component.";
                    }

                    leaf contains-temperature-sensor {
                        type boolean;
                        description
                            "Indicates whether or not this hardware component contains
                             a temperature sensor.";
                    }

                    leaf temperature {
                        type int32;
                        description
                            "Indicates the current temperature in degrees celsius from
                             the temperature sensor.";
                    }

                    leaf temperature-threshold {
                        type int32;
                        description
                            "Indicates the temperature threshold for this hardware
                             component in degrees celsius.";
                    }

                    leaf over-temperature-status {
                        type enumeration {
                            enum ok                             { value 1; }
                            enum over-temp                      { value 2; }
                        }
                        description
                            "Indicates whether the temperature of the hardware component has exceeded
                             its threshold. If that temperature has been exceeded, a value of
                             'over-temp' (2) will be reported.";
                    }

                    leaf alarm-state {
                        type enumeration {
                            enum unknown                        { value 0; }
                            enum alarm-active                   { value 1; }
                            enum alarm-cleared                  { value 2; }
                        }
                        description
                            "Indicates the current alarm state for this hardware
                             component.";
                    }

                    leaf manufacturing-deviations {
                        type string {
                            length "0..255";
                        }
                        description
                            "Indicates the record of changes done by the manfacturing
                             to the hardware or software which is outside the normal
                             revision control process.";
                    }

                    leaf manufacturing-assembly-number {
                        type string {
                            length "0..32";
                        }
                        description
                            "Indicates an assembly number indicating manufacturing
                             differences for a given part number.";
                    }

                    leaf power-zone-location {
                        type uint32 {
                            range "0..32";
                        }
                        description
                            "Indicates the managed power zone that this hardware
                             component resides.";
                    }

                } // container hardware-data

                container hardware-resource {
                    description "Enter the hardware-resource context";

                    container amperage {
                        description "Enter the amperage context";

                        leaf current {
                            type int32;
                            units "milliamperes";
                            description
                                "Indicates the current amperage use of the managed hardware component
                                 in milli-Amperes (mA).";
                        }

                        leaf minimum {
                            type int32;
                            units "milliamperes";
                            description
                                "Indicates the lowest amperage use of the managed hardware component
                                 in milli-Amperes (mA), recorded at the time indicated by
                                 minimum-time";
                        }

                        leaf minimum-time {
                            type yang:date-and-time;
                            description "Indicates the time and date at which minimum amperage was last updated.";
                        }

                        leaf peak {
                            type int32;
                            units "milliamperes";
                            description
                                "Indicates the peak amperage use of the managed hardware component
                                 in milli-Amperes (mA), recorded at the time indicated by
                                 peak-time.";
                        }

                        leaf peak-time {
                            type yang:date-and-time;
                            description "Indicates the time and date at which peak amperage was last updated";
                        }

                    } // container amperage

                    container voltage {
                        description "Enter the voltage context";

                        leaf current {
                            type int32;
                            units "millivolts";
                            description
                                "Indicates the current voltage use of the managed hardware component
                                 in milli-Volts (mV).";
                        }

                        leaf minimum {
                            type int32;
                            units "millivolts";
                            description
                                "Indicates the lowest voltage use of the managed hardware component
                                 in milli-Volts (mV), last recorded at the time indicated by
                                 minimum-time";
                        }

                        leaf minimum-time {
                            type yang:date-and-time;
                            description "Indicates the time and date at which minimum voltage was last updated.";
                        }

                        leaf peak {
                            type int32;
                            units "millivolts";
                            description
                                "Indicates the peak voltage use of the managed hardware component
                                 in milli-Volts (mV), last recorded at the time indicated by
                                 peak-time.";
                        }

                        leaf peak-time {
                            type yang:date-and-time;
                            description "Indicates the time and date at which peak voltage was last updated";
                        }

                    } // container voltage

                    container wattage {
                        description "Enter the wattage context";

                        leaf current {
                            type int32;
                            units "milliwatts";
                            description
                                "Indicates the current wattage use of the managed hardware component
                                 in milli-Watts (mW).";
                        }

                        leaf minimum {
                            type int32;
                            units "milliwatts";
                            description
                                "Indicates the lowest wattage use of the managed hardware component
                                 in milli-Watts (mW), last recorded at the time indicated by
                                 minimum-time";
                        }

                        leaf minimum-time {
                            type yang:date-and-time;
                            description "Indicates the time and date at which minimum wattage was last updated.";
                        }

                        leaf peak {
                            type int32;
                            units "milliwatts";
                            description
                                "Indicates the peak wattage use of the managed hardware component
                                 in milli-Watts (mW), last recorded at the time indicated by
                                 peak-time.";
                        }

                        leaf peak-time {
                            type yang:date-and-time;
                            description "Indicates the time and date at which was last updated";
                        }

                        leaf required {
                            type int32;
                            units "milliwatts";
                            description
                                "Indicates the wattage required by the managed hardware component
                                 in milli-Watts (mW).";
                        }

                    } // container wattage

                } // container hardware-resource

            } // list chassis-control-module

            container cpm-module-adapter {
                description "Enter the cpm-module-adapter context";

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description
                            "Indicates the CLEI, a unique 10-character identifier fixed
                             by the manufacturer.";
                    }

                    leaf field-replaceable-unit {
                        type boolean;
                        description
                            "Indicates whether the hardware component is a field
                             replaceable unit or not.";
                    }

                    leaf contains-temperature-sensor {
                        type boolean;
                        description
                            "Indicates whether or not this hardware component contains
                             a temperature sensor.";
                    }

                    leaf alarm-state {
                        type enumeration {
                            enum unknown                        { value 0; }
                            enum alarm-active                   { value 1; }
                            enum alarm-cleared                  { value 2; }
                        }
                        description
                            "Indicates the current alarm state for this hardware
                             component.";
                    }

                    leaf manufacturing-deviations {
                        type string {
                            length "0..255";
                        }
                        description
                            "Indicates the record of changes done by the manfacturing
                             to the hardware or software which is outside the normal
                             revision control process.";
                    }

                    leaf manufacturing-assembly-number {
                        type string {
                            length "0..32";
                        }
                        description
                            "Indicates an assembly number indicating manufacturing
                             differences for a given part number.";
                    }

                } // container hardware-data

                container hardware-resource {
                    description "Enter the hardware-resource context";

                    container amperage {
                        description "Enter the amperage context";

                        leaf current {
                            type int32;
                            units "milliamperes";
                            description
                                "Indicates the current amperage use of the managed hardware component
                                 in milli-Amperes (mA).";
                        }

                        leaf minimum {
                            type int32;
                            units "milliamperes";
                            description
                                "Indicates the lowest amperage use of the managed hardware component
                                 in milli-Amperes (mA), recorded at the time indicated by
                                 minimum-time";
                        }

                        leaf minimum-time {
                            type yang:date-and-time;
                            description "Indicates the time and date at which minimum amperage was last updated.";
                        }

                        leaf peak {
                            type int32;
                            units "milliamperes";
                            description
                                "Indicates the peak amperage use of the managed hardware component
                                 in milli-Amperes (mA), recorded at the time indicated by
                                 peak-time.";
                        }

                        leaf peak-time {
                            type yang:date-and-time;
                            description "Indicates the time and date at which peak amperage was last updated";
                        }

                    } // container amperage

                    container voltage {
                        description "Enter the voltage context";

                        leaf current {
                            type int32;
                            units "millivolts";
                            description
                                "Indicates the current voltage use of the managed hardware component
                                 in milli-Volts (mV).";
                        }

                        leaf minimum {
                            type int32;
                            units "millivolts";
                            description
                                "Indicates the lowest voltage use of the managed hardware component
                                 in milli-Volts (mV), last recorded at the time indicated by
                                 minimum-time";
                        }

                        leaf minimum-time {
                            type yang:date-and-time;
                            description "Indicates the time and date at which minimum voltage was last updated.";
                        }

                        leaf peak {
                            type int32;
                            units "millivolts";
                            description
                                "Indicates the peak voltage use of the managed hardware component
                                 in milli-Volts (mV), last recorded at the time indicated by
                                 peak-time.";
                        }

                        leaf peak-time {
                            type yang:date-and-time;
                            description "Indicates the time and date at which peak voltage was last updated";
                        }

                    } // container voltage

                    container wattage {
                        description "Enter the wattage context";

                        leaf current {
                            type int32;
                            units "milliwatts";
                            description
                                "Indicates the current wattage use of the managed hardware component
                                 in milli-Watts (mW).";
                        }

                        leaf minimum {
                            type int32;
                            units "milliwatts";
                            description
                                "Indicates the lowest wattage use of the managed hardware component
                                 in milli-Watts (mW), last recorded at the time indicated by
                                 minimum-time";
                        }

                        leaf minimum-time {
                            type yang:date-and-time;
                            description "Indicates the time and date at which minimum wattage was last updated.";
                        }

                        leaf peak {
                            type int32;
                            units "milliwatts";
                            description
                                "Indicates the peak wattage use of the managed hardware component
                                 in milli-Watts (mW), last recorded at the time indicated by
                                 peak-time.";
                        }

                        leaf peak-time {
                            type yang:date-and-time;
                            description "Indicates the time and date at which was last updated";
                        }

                        leaf required {
                            type int32;
                            units "milliwatts";
                            description
                                "Indicates the wattage required by the managed hardware component
                                 in milli-Watts (mW).";
                        }

                    } // container wattage

                } // container hardware-resource

            } // container cpm-module-adapter

            list fan {
                key "fan-slot";
                description "Enter the fan list instance";

                leaf fan-slot {
                    type uint32 {
                        range "1..31";
                    }
                    description "The unique identifier index for a fan tray in the chassis.";
                }

                leaf state {
                    type types-system:device-state;
                    description "The device state of the physical fan tray.";
                }

                leaf revision {
                    type enumeration {
                        enum unknown                        { value 0; }
                        enum original-fan-tray              { value 1; }
                        enum high-flow-fan-tray             { value 2; }
                    }
                    description "The revision of the physical fan tray.";
                }

                leaf speed {
                    type types-sros:percent;
                    description
                        "The speed of the fans in the physical fan tray as a percentage
                         of the maximum speed.";
                }

                leaf type {
                    type enumeration {
                        enum chassis                        { value 1; }
                        enum pcm                            { value 2; }
                    }
                    description "The type of physical fan tray.";
                }

                leaf airflow-direction {
                    type enumeration {
                        enum unknown                        { value 0; }
                        enum front-to-back                  { value 1; }
                        enum back-to-front                  { value 2; }
                        enum right-to-left                  { value 3; }
                    }
                    description "If the fan direction is 'front-to-back' or 'back-to-front' or 'right-to-left'.";
                }

                leaf equipped-fan-module-type {
                    type enumeration {
                        enum unknown                        { value 0; }
                        enum fan-sar-10x-f                  { value 2; }
                        enum fan-sar-10x-r                  { value 3; }
                    }
                    description "The type of fan tray module that is physically inserted.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description
                            "Indicates the CLEI, a unique 10-character identifier fixed
                             by the manufacturer.";
                    }

                    leaf field-replaceable-unit {
                        type boolean;
                        description
                            "Indicates whether the hardware component is a field
                             replaceable unit or not.";
                    }

                    leaf oper-state {
                        type types-chassis:hw-oper-state;
                        description "Indicates the operational status of the hardware component.";
                    }

                    leaf failure-reason {
                        type string {
                            length "0..255";
                        }
                        description
                            "Indicates the reason why a hardware component 'failed' as
                             indicated in oper-state.";
                    }

                    leaf alarm-state {
                        type enumeration {
                            enum unknown                        { value 0; }
                            enum alarm-active                   { value 1; }
                            enum alarm-cleared                  { value 2; }
                        }
                        description
                            "Indicates the current alarm state for this hardware
                             component.";
                    }

                    leaf manufacturing-deviations {
                        type string {
                            length "0..255";
                        }
                        description
                            "Indicates the record of changes done by the manfacturing
                             to the hardware or software which is outside the normal
                             revision control process.";
                    }

                    leaf equipped-platform-type {
                        type types-chassis:equipped-platform-type;
                        description
                            "Indicates the platform type of the installed hardware
                             component, as read from the EEPROM.";
                    }

                    leaf manufacturing-assembly-number {
                        type string {
                            length "0..32";
                        }
                        description
                            "Indicates an assembly number indicating manufacturing
                             differences for a given part number.";
                    }

                    leaf power-zone-location {
                        type uint32 {
                            range "0..32";
                        }
                        description
                            "Indicates the managed power zone that this hardware
                             component resides.";
                    }

                    leaf software-last-boot-time {
                        type yang:date-and-time;
                        description
                            "This indicates the date and time the software running on this
                             hardware component was last rebooted.";
                    }

                    leaf firmware-revision-status {
                        type enumeration {
                            enum not-applicable                 { value 0; }
                            enum acceptable                     { value 1; }
                            enum not-acceptable                 { value 2; }
                            enum upgrade-pending                { value 3; }
                            enum upgrading                      { value 4; }
                            enum upgrade-next-hard-reset        { value 5; }
                            enum power-cycle-required           { value 6; }
                        }
                        description
                            "Indicates the firmware/FPGA revision status for the
                             hardware component.";
                    }

                } // container hardware-data

                container hardware-resource {
                    description "Enter the hardware-resource context";

                    container amperage {
                        description "Enter the amperage context";

                        leaf current {
                            type int32;
                            units "milliamperes";
                            description
                                "Indicates the current amperage use of the managed hardware component
                                 in milli-Amperes (mA).";
                        }

                        leaf minimum {
                            type int32;
                            units "milliamperes";
                            description
                                "Indicates the lowest amperage use of the managed hardware component
                                 in milli-Amperes (mA), recorded at the time indicated by
                                 minimum-time";
                        }

                        leaf minimum-time {
                            type yang:date-and-time;
                            description "Indicates the time and date at which minimum amperage was last updated.";
                        }

                        leaf peak {
                            type int32;
                            units "milliamperes";
                            description
                                "Indicates the peak amperage use of the managed hardware component
                                 in milli-Amperes (mA), recorded at the time indicated by
                                 peak-time.";
                        }

                        leaf peak-time {
                            type yang:date-and-time;
                            description "Indicates the time and date at which peak amperage was last updated";
                        }

                    } // container amperage

                    container voltage {
                        description "Enter the voltage context";

                        leaf current {
                            type int32;
                            units "millivolts";
                            description
                                "Indicates the current voltage use of the managed hardware component
                                 in milli-Volts (mV).";
                        }

                        leaf minimum {
                            type int32;
                            units "millivolts";
                            description
                                "Indicates the lowest voltage use of the managed hardware component
                                 in milli-Volts (mV), last recorded at the time indicated by
                                 minimum-time";
                        }

                        leaf minimum-time {
                            type yang:date-and-time;
                            description "Indicates the time and date at which minimum voltage was last updated.";
                        }

                        leaf peak {
                            type int32;
                            units "millivolts";
                            description
                                "Indicates the peak voltage use of the managed hardware component
                                 in milli-Volts (mV), last recorded at the time indicated by
                                 peak-time.";
                        }

                        leaf peak-time {
                            type yang:date-and-time;
                            description "Indicates the time and date at which peak voltage was last updated";
                        }

                    } // container voltage

                    container wattage {
                        description "Enter the wattage context";

                        leaf current {
                            type int32;
                            units "milliwatts";
                            description
                                "Indicates the current wattage use of the managed hardware component
                                 in milli-Watts (mW).";
                        }

                        leaf minimum {
                            type int32;
                            units "milliwatts";
                            description
                                "Indicates the lowest wattage use of the managed hardware component
                                 in milli-Watts (mW), last recorded at the time indicated by
                                 minimum-time";
                        }

                        leaf minimum-time {
                            type yang:date-and-time;
                            description "Indicates the time and date at which minimum wattage was last updated.";
                        }

                        leaf peak {
                            type int32;
                            units "milliwatts";
                            description
                                "Indicates the peak wattage use of the managed hardware component
                                 in milli-Watts (mW), last recorded at the time indicated by
                                 peak-time.";
                        }

                        leaf peak-time {
                            type yang:date-and-time;
                            description "Indicates the time and date at which was last updated";
                        }

                        leaf required {
                            type int32;
                            units "milliwatts";
                            description
                                "Indicates the wattage required by the managed hardware component
                                 in milli-Watts (mW).";
                        }

                    } // container wattage

                } // container hardware-resource

            } // list fan

            list power-supply {
                key "power-supply-id";
                description "Enter the power-supply list instance";

                leaf power-supply-id {
                    type uint32 {
                        range "1..31";
                    }
                    description "The unique identifier index for a power supply tray in the chassis.";
                }

                leaf equipped-type {
                    type enumeration {
                        enum none                           { value 0; }
                        enum dc-single                      { value 1; }
                        enum ac-single                      { value 2; }
                        enum ac-multiple                    { value 3; }
                        enum auto                           { value 4; }
                        enum dc-multiple                    { value 5; }
                        enum not-applicable                 { status obsolete; }
                    }
                    description
                        "Indicates the type of power supply that is physically inserted
                         into the slot.";
                }

                leaf ac-status {
                    type types-system:device-state;
                    description "The input AC voltage state of the power supply.";
                }

                leaf dc-status {
                    type types-system:device-state;
                    description "The output DC voltage state of the power supply.";
                }

                leaf temp-status {
                    type types-system:device-state;
                    description "The current temperature state of the power supply.";
                }

                leaf temp-threshold {
                    type int32;
                    units "degrees celsius";
                    description
                        "The temperature threshold for this power supply
                         tray in degrees celsius.";
                }

                leaf first-power-supply-status {
                    type types-system:device-state;
                    description
                        "The overall status of an equipped power supply.

                         For AC multiple power supplies, this represents the overall status
                         of the first power supply in the tray (or shelf).";
                }

                leaf second-power-supply-status {
                    type types-system:device-state;
                    description
                        "The overall status of an equipped power supply.

                         For AC multiple power supplies, this represents the overall status
                         of the second power supply in the tray (or shelf).";
                }

                leaf input-status {
                    type types-system:device-state;
                    description "The input voltage state of the power supply.";
                }

                leaf output-status {
                    type types-system:device-state;
                    description "The output voltage state of the power supply.";
                }

                leaf pem-type {
                    type enumeration {
                        enum not-applicable                 { value 0; }
                        enum unknown                        { value 1; }
                        enum pem                            { value 2; }
                        enum pem-3                          { value 3; }
                        enum peq                            { value 4; }
                    }
                    description "The Power Entry Module (PEM) type installed in the PEM slot.";
                }

                leaf pem-ac-rect {
                    type bits {
                        bit ac-rect1                       { position 0; }
                        bit ac-rect2                       { position 1; }
                    }
                    description
                        "Which Power Entry Module AC rectifiers installed in the PEM slot
                         are in a failed state or are missing.";
                }

                leaf fan-direction {
                    type enumeration {
                        enum unknown                        { value 0; }
                        enum front-to-back                  { value 1; }
                        enum back-to-front                  { value 2; }
                    }
                    description "If the fan direction is 'front-to-back' or 'back-to-front'.";
                }

                leaf fan-status {
                    type types-system:device-state;
                    description "The operational state of the power-supply fan.";
                }

                leaf input-feed-down {
                    type bits {
                        bit input-feed-a                   { position 0; }
                        bit input-feed-b                   { position 1; }
                    }
                    description "Which input feeds are not supplying power.";
                }

                leaf input-feed-a-voltage {
                    type int32;
                    units "millivolts";
                    description "The input voltage at feed A.";
                }

                leaf input-feed-b-voltage {
                    type int32;
                    units "millivolts";
                    description "The input voltage at feed B.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description
                            "Indicates the CLEI, a unique 10-character identifier fixed
                             by the manufacturer.";
                    }

                    leaf field-replaceable-unit {
                        type boolean;
                        description
                            "Indicates whether the hardware component is a field
                             replaceable unit or not.";
                    }

                    leaf oper-state {
                        type types-chassis:hw-oper-state;
                        description "Indicates the operational status of the hardware component.";
                    }

                    leaf failure-reason {
                        type string {
                            length "0..255";
                        }
                        description
                            "Indicates the reason why a hardware component 'failed' as
                             indicated in oper-state.";
                    }

                    leaf over-temperature-status {
                        type enumeration {
                            enum ok                             { value 1; }
                            enum over-temp                      { value 2; }
                        }
                        description
                            "Indicates whether the temperature of the hardware component has exceeded
                             its threshold. If that temperature has been exceeded, a value of
                             'over-temp' (2) will be reported.";
                    }

                    leaf alarm-state {
                        type enumeration {
                            enum unknown                        { value 0; }
                            enum alarm-active                   { value 1; }
                            enum alarm-cleared                  { value 2; }
                        }
                        description
                            "Indicates the current alarm state for this hardware
                             component.";
                    }

                    leaf manufacturing-deviations {
                        type string {
                            length "0..255";
                        }
                        description
                            "Indicates the record of changes done by the manfacturing
                             to the hardware or software which is outside the normal
                             revision control process.";
                    }

                    leaf equipped-platform-type {
                        type types-chassis:equipped-platform-type;
                        description
                            "Indicates the platform type of the installed hardware
                             component, as read from the EEPROM.";
                    }

                    leaf manufacturing-assembly-number {
                        type string {
                            length "0..32";
                        }
                        description
                            "Indicates an assembly number indicating manufacturing
                             differences for a given part number.";
                    }

                    leaf power-zone-location {
                        type uint32 {
                            range "0..32";
                        }
                        description
                            "Indicates the managed power zone that this hardware
                             component resides.";
                    }

                } // container hardware-data

            } // list power-supply

            list peq {
                key "peq-slot";
                description "Enter the peq list instance";

                leaf peq-slot {
                    type uint32 {
                        range "1..31";
                    }
                    description "The unique identifier index for a power supply tray in the chassis.";
                }

                leaf equipped-type {
                    type types-system:peq-type-state;
                    description
                        "Identifies the CCM type that is physically
                         inserted into this PEQ slot in the chassis.";
                }

                leaf available-wattage {
                    type uint32;
                    units "watts";
                    description "The reported available wattage of the PEQ.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description
                            "Indicates the CLEI, a unique 10-character identifier fixed
                             by the manufacturer.";
                    }

                    leaf field-replaceable-unit {
                        type boolean;
                        description
                            "Indicates whether the hardware component is a field
                             replaceable unit or not.";
                    }

                    leaf oper-state {
                        type types-chassis:hw-oper-state;
                        description "Indicates the operational status of the hardware component.";
                    }

                    leaf failure-reason {
                        type string {
                            length "0..255";
                        }
                        description
                            "Indicates the reason why a hardware component 'failed' as
                             indicated in oper-state.";
                    }

                    leaf over-temperature-status {
                        type enumeration {
                            enum ok                             { value 1; }
                            enum over-temp                      { value 2; }
                        }
                        description
                            "Indicates whether the temperature of the hardware component has exceeded
                             its threshold. If that temperature has been exceeded, a value of
                             'over-temp' (2) will be reported.";
                    }

                    leaf alarm-state {
                        type enumeration {
                            enum unknown                        { value 0; }
                            enum alarm-active                   { value 1; }
                            enum alarm-cleared                  { value 2; }
                        }
                        description
                            "Indicates the current alarm state for this hardware
                             component.";
                    }

                    leaf manufacturing-deviations {
                        type string {
                            length "0..255";
                        }
                        description
                            "Indicates the record of changes done by the manfacturing
                             to the hardware or software which is outside the normal
                             revision control process.";
                    }

                    leaf equipped-platform-type {
                        type types-chassis:equipped-platform-type;
                        description
                            "Indicates the platform type of the installed hardware
                             component, as read from the EEPROM.";
                    }

                    leaf manufacturing-assembly-number {
                        type string {
                            length "0..32";
                        }
                        description
                            "Indicates an assembly number indicating manufacturing
                             differences for a given part number.";
                    }

                    leaf power-zone-location {
                        type uint32 {
                            range "0..32";
                        }
                        description
                            "Indicates the managed power zone that this hardware
                             component resides.";
                    }

                    leaf software-last-boot-time {
                        type yang:date-and-time;
                        description
                            "This indicates the date and time the software running on this
                             hardware component was last rebooted.";
                    }

                    leaf firmware-revision-status {
                        type enumeration {
                            enum not-applicable                 { value 0; }
                            enum acceptable                     { value 1; }
                            enum not-acceptable                 { value 2; }
                            enum upgrade-pending                { value 3; }
                            enum upgrading                      { value 4; }
                            enum upgrade-next-hard-reset        { value 5; }
                            enum power-cycle-required           { value 6; }
                        }
                        description
                            "Indicates the firmware/FPGA revision status for the
                             hardware component.";
                    }

                } // container hardware-data

            } // list peq

            list power-connection-module {
                key "pcm-slot";
                description "Enter the power-connection-module list instance";

                leaf pcm-slot {
                    type uint32 {
                        range "1..12";
                    }
                    description "The unique identifier index for a power control module in the chassis.";
                }

                leaf equipped-type {
                    type types-chassis:pcm-type-state;
                    description "The equipped PCM type.";
                }

                leaf input-feed-down {
                    type bits {
                        bit input-feed-a                   { position 0; }
                        bit input-feed-b2                  { position 1; }
                        bit input-feed-a2                  { position 2; }
                        bit input-feed-b                   { position 3; }
                    }
                    description "Indicates which feeds are down on the quad pcm.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description
                            "Indicates the CLEI, a unique 10-character identifier fixed
                             by the manufacturer.";
                    }

                    leaf field-replaceable-unit {
                        type boolean;
                        description
                            "Indicates whether the hardware component is a field
                             replaceable unit or not.";
                    }

                    leaf oper-state {
                        type types-chassis:hw-oper-state;
                        description "Indicates the operational status of the hardware component.";
                    }

                    leaf failure-reason {
                        type string {
                            length "0..255";
                        }
                        description
                            "Indicates the reason why a hardware component 'failed' as
                             indicated in oper-state.";
                    }

                    leaf alarm-state {
                        type enumeration {
                            enum unknown                        { value 0; }
                            enum alarm-active                   { value 1; }
                            enum alarm-cleared                  { value 2; }
                        }
                        description
                            "Indicates the current alarm state for this hardware
                             component.";
                    }

                    leaf manufacturing-deviations {
                        type string {
                            length "0..255";
                        }
                        description
                            "Indicates the record of changes done by the manfacturing
                             to the hardware or software which is outside the normal
                             revision control process.";
                    }

                    leaf equipped-platform-type {
                        type types-chassis:equipped-platform-type;
                        description
                            "Indicates the platform type of the installed hardware
                             component, as read from the EEPROM.";
                    }

                    leaf manufacturing-assembly-number {
                        type string {
                            length "0..32";
                        }
                        description
                            "Indicates an assembly number indicating manufacturing
                             differences for a given part number.";
                    }

                    leaf power-zone-location {
                        type uint32 {
                            range "0..32";
                        }
                        description
                            "Indicates the managed power zone that this hardware
                             component resides.";
                    }

                    leaf software-last-boot-time {
                        type yang:date-and-time;
                        description
                            "This indicates the date and time the software running on this
                             hardware component was last rebooted.";
                    }

                    leaf firmware-code-version {
                        type string {
                            length "0..255";
                        }
                        description
                            "Indicates the software product release version number
                             associated with the firmware version currently programmed.";
                    }

                    leaf firmware-revision-status {
                        type enumeration {
                            enum not-applicable                 { value 0; }
                            enum acceptable                     { value 1; }
                            enum not-acceptable                 { value 2; }
                            enum upgrade-pending                { value 3; }
                            enum upgrading                      { value 4; }
                            enum upgrade-next-hard-reset        { value 5; }
                            enum power-cycle-required           { value 6; }
                        }
                        description
                            "Indicates the firmware/FPGA revision status for the
                             hardware component.";
                    }

                } // container hardware-data

            } // list power-connection-module

            list power-module {
                key "power-module-id";
                description "Enter the power-module list instance";

                leaf power-module-id {
                    type uint32 {
                        range "1..12";
                    }
                    description "The unique identifier index for a power shelf in the chassis.";
                }

                leaf equipped-type {
                    type types-chassis:power-module-type-state;
                    description
                        "Identifies the power module type that is physically
                         inserted into this shelf in the chassis.";
                }

                leaf output-status {
                    type enumeration {
                        enum unknown                        { value 0; }
                        enum ok                             { value 1; }
                        enum failed                         { value 2; }
                        enum disabled                       { value 3; }
                        enum not-equipped                   { value 4; }
                    }
                    description "The output voltage state of the power supply.";
                }

                leaf available-wattage {
                    type uint32;
                    units "watts";
                    description "The reported available wattage of the power module.";
                }

                leaf input-feed-down {
                    type bits {
                        bit input-feed-a                   { position 0; }
                        bit input-feed-b                   { position 1; }
                    }
                    description "Which input feeds are not supplying power.";
                }

                leaf input-feed-a-voltage {
                    type int32;
                    units "millivolts";
                    description "The input voltage at feed A.";
                }

                leaf input-feed-b-voltage {
                    type int32;
                    units "millivolts";
                    description "The input voltage at feed B.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description
                            "Indicates the CLEI, a unique 10-character identifier fixed
                             by the manufacturer.";
                    }

                    leaf field-replaceable-unit {
                        type boolean;
                        description
                            "Indicates whether the hardware component is a field
                             replaceable unit or not.";
                    }

                    leaf oper-state {
                        type types-chassis:hw-oper-state;
                        description "Indicates the operational status of the hardware component.";
                    }

                    leaf failure-reason {
                        type string {
                            length "0..255";
                        }
                        description
                            "Indicates the reason why a hardware component 'failed' as
                             indicated in oper-state.";
                    }

                    leaf over-temperature-status {
                        type enumeration {
                            enum ok                             { value 1; }
                            enum over-temp                      { value 2; }
                        }
                        description
                            "Indicates whether the temperature of the hardware component has exceeded
                             its threshold. If that temperature has been exceeded, a value of
                             'over-temp' (2) will be reported.";
                    }

                    leaf alarm-state {
                        type enumeration {
                            enum unknown                        { value 0; }
                            enum alarm-active                   { value 1; }
                            enum alarm-cleared                  { value 2; }
                        }
                        description
                            "Indicates the current alarm state for this hardware
                             component.";
                    }

                    leaf manufacturing-deviations {
                        type string {
                            length "0..255";
                        }
                        description
                            "Indicates the record of changes done by the manfacturing
                             to the hardware or software which is outside the normal
                             revision control process.";
                    }

                    leaf equipped-platform-type {
                        type types-chassis:equipped-platform-type;
                        description
                            "Indicates the platform type of the installed hardware
                             component, as read from the EEPROM.";
                    }

                    leaf manufacturing-assembly-number {
                        type string {
                            length "0..32";
                        }
                        description
                            "Indicates an assembly number indicating manufacturing
                             differences for a given part number.";
                    }

                    leaf power-zone-location {
                        type uint32 {
                            range "0..32";
                        }
                        description
                            "Indicates the managed power zone that this hardware
                             component resides.";
                    }

                    leaf software-last-boot-time {
                        type yang:date-and-time;
                        description
                            "This indicates the date and time the software running on this
                             hardware component was last rebooted.";
                    }

                    leaf firmware-revision-status {
                        type enumeration {
                            enum not-applicable                 { value 0; }
                            enum acceptable                     { value 1; }
                            enum not-acceptable                 { value 2; }
                            enum upgrade-pending                { value 3; }
                            enum upgrading                      { value 4; }
                            enum upgrade-next-hard-reset        { value 5; }
                            enum power-cycle-required           { value 6; }
                        }
                        description
                            "Indicates the firmware/FPGA revision status for the
                             hardware component.";
                    }

                } // container hardware-data

            } // list power-module

            list power-shelf {
                key "power-shelf-id";
                description "Enter the power-shelf list instance";

                leaf power-shelf-id {
                    type uint32 {
                        range "1..2";
                    }
                    description "The unique identifier index for a power shelf in the chassis.";
                }

                leaf equipped-type {
                    type types-chassis:power-shelf-type-state;
                    description
                        "Identifies the power shelf type that is physically
                         inserted into this chassis.";
                }

                leaf input-power-mode {
                    type uint32 {
                        range "0|60|80";
                    }
                    units "amperes";
                    description "The the input power mode of the power shelf.";
                }

                leaf output-status {
                    type enumeration {
                        enum unknown                        { value 0; }
                        enum on                             { value 1; }
                        enum off                            { value 2; }
                        enum not-equipped                   { value 3; }
                    }
                    description "The output status of the power shelf.";
                }

                leaf power-shelf-comms-fail {
                    type types-chassis:cpm-comms-fail-state;
                    description "Which CPM(s) cannot communicate with the power-shelf.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description
                            "Indicates the CLEI, a unique 10-character identifier fixed
                             by the manufacturer.";
                    }

                    leaf field-replaceable-unit {
                        type boolean;
                        description
                            "Indicates whether the hardware component is a field
                             replaceable unit or not.";
                    }

                    leaf oper-state {
                        type types-chassis:hw-oper-state;
                        description "Indicates the operational status of the hardware component.";
                    }

                    leaf failure-reason {
                        type string {
                            length "0..255";
                        }
                        description
                            "Indicates the reason why a hardware component 'failed' as
                             indicated in oper-state.";
                    }

                    leaf over-temperature-status {
                        type enumeration {
                            enum ok                             { value 1; }
                            enum over-temp                      { value 2; }
                        }
                        description
                            "Indicates whether the temperature of the hardware component has exceeded
                             its threshold. If that temperature has been exceeded, a value of
                             'over-temp' (2) will be reported.";
                    }

                    leaf alarm-state {
                        type enumeration {
                            enum unknown                        { value 0; }
                            enum alarm-active                   { value 1; }
                            enum alarm-cleared                  { value 2; }
                        }
                        description
                            "Indicates the current alarm state for this hardware
                             component.";
                    }

                    leaf manufacturing-deviations {
                        type string {
                            length "0..255";
                        }
                        description
                            "Indicates the record of changes done by the manfacturing
                             to the hardware or software which is outside the normal
                             revision control process.";
                    }

                    leaf equipped-platform-type {
                        type types-chassis:equipped-platform-type;
                        description
                            "Indicates the platform type of the installed hardware
                             component, as read from the EEPROM.";
                    }

                    leaf manufacturing-assembly-number {
                        type string {
                            length "0..32";
                        }
                        description
                            "Indicates an assembly number indicating manufacturing
                             differences for a given part number.";
                    }

                    leaf power-zone-location {
                        type uint32 {
                            range "0..32";
                        }
                        description
                            "Indicates the managed power zone that this hardware
                             component resides.";
                    }

                    leaf software-last-boot-time {
                        type yang:date-and-time;
                        description
                            "This indicates the date and time the software running on this
                             hardware component was last rebooted.";
                    }

                    leaf firmware-revision-status {
                        type enumeration {
                            enum not-applicable                 { value 0; }
                            enum acceptable                     { value 1; }
                            enum not-acceptable                 { value 2; }
                            enum upgrade-pending                { value 3; }
                            enum upgrading                      { value 4; }
                            enum upgrade-next-hard-reset        { value 5; }
                            enum power-cycle-required           { value 6; }
                        }
                        description
                            "Indicates the firmware/FPGA revision status for the
                             hardware component.";
                    }

                } // container hardware-data

                container controller-card {
                    description "Enter the controller-card context";

                    container hardware-data {
                        description "Enter the hardware-data context";

                        leaf part-number {
                            type string {
                                length "0..32";
                            }
                            description "Indicates the part number information.";
                        }

                        leaf serial-number {
                            type string {
                                length "0..32";
                            }
                            description "Indicates the serial number of the hardware component.";
                        }

                        leaf manufacturing-date {
                            type string {
                                length "0..8";
                            }
                            description "Indicates the manufacturing date of the hardware component.";
                        }

                        leaf common-language-equipment-identifier {
                            type string {
                                length "0..10";
                            }
                            description
                                "Indicates the CLEI, a unique 10-character identifier fixed
                                 by the manufacturer.";
                        }

                        leaf field-replaceable-unit {
                            type boolean;
                            description
                                "Indicates whether the hardware component is a field
                                 replaceable unit or not.";
                        }

                        leaf oper-state {
                            type types-chassis:hw-oper-state;
                            description "Indicates the operational status of the hardware component.";
                        }

                        leaf contains-temperature-sensor {
                            type boolean;
                            description
                                "Indicates whether or not this hardware component contains
                                 a temperature sensor.";
                        }

                        leaf alarm-state {
                            type enumeration {
                                enum unknown                        { value 0; }
                                enum alarm-active                   { value 1; }
                                enum alarm-cleared                  { value 2; }
                            }
                            description
                                "Indicates the current alarm state for this hardware
                                 component.";
                        }

                        leaf manufacturing-deviations {
                            type string {
                                length "0..255";
                            }
                            description
                                "Indicates the record of changes done by the manfacturing
                                 to the hardware or software which is outside the normal
                                 revision control process.";
                        }

                        leaf manufacturing-assembly-number {
                            type string {
                                length "0..32";
                            }
                            description
                                "Indicates an assembly number indicating manufacturing
                                 differences for a given part number.";
                        }

                        leaf software-last-boot-time {
                            type yang:date-and-time;
                            description
                                "This indicates the date and time the software running on this
                                 hardware component was last rebooted.";
                        }

                    } // container hardware-data

                } // container controller-card

                list power-module {
                    key "power-module-id";
                    description "Enter the power-module list instance";

                    leaf power-module-id {
                        type uint32 {
                            range "1..12";
                        }
                        description "The unique identifier index for a power shelf in the chassis.";
                    }

                    leaf equipped-type {
                        type types-chassis:power-module-type-state;
                        description
                            "Identifies the power module type that is physically
                             inserted into this shelf in the chassis.";
                    }

                    leaf output-status {
                        type enumeration {
                            enum unknown                        { value 0; }
                            enum ok                             { value 1; }
                            enum failed                         { value 2; }
                            enum disabled                       { value 3; }
                            enum not-equipped                   { value 4; }
                        }
                        description "The output voltage state of the power supply.";
                    }

                    leaf available-wattage {
                        type uint32;
                        units "watts";
                        description "The reported available wattage of the power module.";
                    }

                    leaf input-feed-down {
                        type bits {
                            bit input-feed-a                   { position 0; }
                            bit input-feed-b                   { position 1; }
                        }
                        description "Which input feeds are not supplying power.";
                    }

                    leaf input-feed-a-voltage {
                        type int32;
                        units "millivolts";
                        description "The input voltage at feed A.";
                    }

                    leaf input-feed-b-voltage {
                        type int32;
                        units "millivolts";
                        description "The input voltage at feed B.";
                    }

                    container hardware-data {
                        description "Enter the hardware-data context";

                        leaf part-number {
                            type string {
                                length "0..32";
                            }
                            description "Indicates the part number information.";
                        }

                        leaf serial-number {
                            type string {
                                length "0..32";
                            }
                            description "Indicates the serial number of the hardware component.";
                        }

                        leaf manufacturing-date {
                            type string {
                                length "0..8";
                            }
                            description "Indicates the manufacturing date of the hardware component.";
                        }

                        leaf common-language-equipment-identifier {
                            type string {
                                length "0..10";
                            }
                            description
                                "Indicates the CLEI, a unique 10-character identifier fixed
                                 by the manufacturer.";
                        }

                        leaf field-replaceable-unit {
                            type boolean;
                            description
                                "Indicates whether the hardware component is a field
                                 replaceable unit or not.";
                        }

                        leaf oper-state {
                            type types-chassis:hw-oper-state;
                            description "Indicates the operational status of the hardware component.";
                        }

                        leaf failure-reason {
                            type string {
                                length "0..255";
                            }
                            description
                                "Indicates the reason why a hardware component 'failed' as
                                 indicated in oper-state.";
                        }

                        leaf over-temperature-status {
                            type enumeration {
                                enum ok                             { value 1; }
                                enum over-temp                      { value 2; }
                            }
                            description
                                "Indicates whether the temperature of the hardware component has exceeded
                                 its threshold. If that temperature has been exceeded, a value of
                                 'over-temp' (2) will be reported.";
                        }

                        leaf alarm-state {
                            type enumeration {
                                enum unknown                        { value 0; }
                                enum alarm-active                   { value 1; }
                                enum alarm-cleared                  { value 2; }
                            }
                            description
                                "Indicates the current alarm state for this hardware
                                 component.";
                        }

                        leaf manufacturing-deviations {
                            type string {
                                length "0..255";
                            }
                            description
                                "Indicates the record of changes done by the manfacturing
                                 to the hardware or software which is outside the normal
                                 revision control process.";
                        }

                        leaf equipped-platform-type {
                            type types-chassis:equipped-platform-type;
                            description
                                "Indicates the platform type of the installed hardware
                                 component, as read from the EEPROM.";
                        }

                        leaf manufacturing-assembly-number {
                            type string {
                                length "0..32";
                            }
                            description
                                "Indicates an assembly number indicating manufacturing
                                 differences for a given part number.";
                        }

                        leaf power-zone-location {
                            type uint32 {
                                range "0..32";
                            }
                            description
                                "Indicates the managed power zone that this hardware
                                 component resides.";
                        }

                        leaf software-last-boot-time {
                            type yang:date-and-time;
                            description
                                "This indicates the date and time the software running on this
                                 hardware component was last rebooted.";
                        }

                        leaf firmware-revision-status {
                            type enumeration {
                                enum not-applicable                 { value 0; }
                                enum acceptable                     { value 1; }
                                enum not-acceptable                 { value 2; }
                                enum upgrade-pending                { value 3; }
                                enum upgrading                      { value 4; }
                                enum upgrade-next-hard-reset        { value 5; }
                                enum power-cycle-required           { value 6; }
                            }
                            description
                                "Indicates the firmware/FPGA revision status for the
                                 hardware component.";
                        }

                    } // container hardware-data

                } // list power-module

            } // list power-shelf

            list flash {
                key "flash-id";
                description "Enter the flash list instance";

                leaf flash-id {
                    type types-system:cpm-flash-id;
                    description "The unique identifier index for a flash device.";
                }

                leaf oper-state {
                    type types-system:device-state;
                    description "Current status of this flash unit.";
                }

                leaf serial-number {
                    type types-sros:description-or-empty;
                    description "The serial number for this flash unit.";
                }

                leaf firmware-revision {
                    type types-sros:description-or-empty;
                    description "The firmware revision number for this flash unit.";
                }

                leaf model-number {
                    type types-sros:description-or-empty;
                    description "The model number for this flash unit.";
                }

                leaf capacity {
                    type uint32;
                    units "kilobytes";
                    description "Indicates the maximum size of this flash unit.";
                }

                leaf free-space {
                    type uint32;
                    units "kilobytes";
                    description "Indicates the amount of free space remaining on this flash unit.";
                }

                leaf percent-used {
                    type uint32;
                    units "percent";
                    description
                        "Indicates the amount used for this flash unit as a percentage
                         of total capacity.";
                }

            } // list flash

        } // list chassis

    } // grouping state-chassis

}
