submodule nokia-state-submgt-up-resiliency {

    yang-version "1.1";

    belongs-to nokia-state { prefix "state"; }

    import nokia-sros-yang-extensions     { prefix "sros-ext"; }
    import nokia-types-sros               { prefix "types-sros"; }

    sros-ext:sros-major-release "rel26";
    organization "Nokia";
    contact
        "Nokia SR OS Support
         Web: <http://www.nokia.com>";
    description
        "Nokia YANG Data model with operational state for subscriber management CUPS UP resiliency on SR OS based routers.

         Copyright 2016 Nokia. All rights reserved. Reproduction of this document
         is authorized on the condition that the foregoing copyright notice is included.

         This nokia-state-submgt-up-resiliency YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping state-submgt-up-resiliency {
        container up-resiliency {
            description "Enter the up-resiliency context";

            list fate-sharing-group-template {
                key "name";
                description "Enter the fate-sharing-group-template list instance";

                leaf name {
                    type types-sros:named-item;
                    description "Textual identification for the fate-sharing-group template";
                }

                leaf last-changed {
                    type types-sros:date-time;
                }

            } // list fate-sharing-group-template

        } // container up-resiliency

    } // grouping state-submgt-up-resiliency

}
