submodule nokia-state-port-eth-access {

    yang-version "1.1";

    belongs-to nokia-state { prefix "state"; }

    import ietf-yang-types                { prefix "yang"; }
    import nokia-sros-yang-extensions     { prefix "sros-ext"; }
    import nokia-types-qos                { prefix "types-qos"; }
    import nokia-types-sros               { prefix "types-sros"; }
    import nokia-types-subscriber-mgmt    { prefix "types-submgt"; }

    include nokia-state-qos;

    sros-ext:sros-major-release "rel26";
    organization "Nokia";
    contact
        "Nokia SR OS Support
         Web: <http://www.nokia.com>";
    description
        "Nokia YANG Data model with operational state for access capabilities for ethernet ports on SR OS based routers.

         Copyright 2016 Nokia. All rights reserved. Reproduction of this document
         is authorized on the condition that the foregoing copyright notice is included.

         This nokia-state-port-eth-access YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping state-port-eth-access {
        container access {
            description "Enter the access context";

            leaf available-bandwidth {
                type yang:counter64;
                units "kilobps";
                description "Indicates the bandwidth that is still free for booking on the Ethernet port.";
            }

            leaf booked-bandwidth {
                type yang:counter64;
                units "kilobps";
                description "Indicates the bandwidth that has been booked on the Ethernet port.";
            }

            container egress {
                description "Enter the egress context";

                list queue-group {
                    key "queue-group-name instance-id";
                    description "Enter the queue-group list instance";

                    leaf queue-group-name {
                        type leafref {
                            path "../../../../../../qos/queue-group-templates/egress/queue-group/egress-queue-group-name";
                        }
                        description "Specifies the queue-group name.";
                    }

                    leaf instance-id {
                        type uint16 {
                            range "1..65535";
                        }
                        description "Specifies the instance identifier.";
                    }

                    container aggregate-rate {
                        description "Enter the aggregate-rate context";

                        leaf operational-rate {
                            type uint32;
                            description "Operational rate information for SAP when using classic port scheduling";
                        }

                        container agg-shaper {
                            description "Enter the agg-shaper context";

                            leaf oper-burst-limit {
                                type int32;
                                description "Burst-Limit information for hardware aggregate shapers";
                            }

                            leaf oper-agg-shaper-rate {
                                type uint32;
                                description "Operational rate information for hardware aggregate shapers";
                            }

                        } // container agg-shaper

                    } // container aggregate-rate

                    container aggregate-shapers {
                        description "Enter the aggregate-shapers context";

                        leaf burst-limit {
                            type int32;
                            units "bytes";
                            description "Operational burst";
                        }

                        leaf depth {
                            type uint32;
                            units "bytes";
                            description "Leaky-bucket depth of the aggregate shaper PIR";
                        }

                        leaf packet-mode {
                            type types-qos:packet-mode;
                            description "Packet-mode";
                        }

                        leaf out-of-date {
                            type boolean;
                            description
                                "Info is out-of-date with respect to the latest config; the
                                 shaper-algorithm still needs to re-calculate the implemented
                                 rate.";
                        }

                        leaf queue-set-size {
                            type int32;
                            description "Queue set size";
                        }

                        leaf queue-set-size-overridden {
                            type boolean;
                            description
                                "Info queue-set-size-overridden is set to true when the shaper is created by
                                 the override configured for sap egress qos policy. When it is set to false,
                                 it indicates that fp-resource-policy default-size setting is used to create
                                 this shaper.";
                        }

                        container rate {
                            description "Enter the rate context";

                            leaf assigned {
                                type uint32;
                                units "kilobps";
                                description "Rate assigned by a hw-agg-shaper-scheduler";
                            }

                            leaf implemented {
                                type uint32;
                                units "kilobps";
                                description
                                    "Implemented rate (based on hardware restrictions and based
                                     on avg-frame-overhead and ATM adjustments)";
                            }

                            leaf consumed {
                                type uint32;
                                units "kilobps";
                                description
                                    "Sum of the rates of the queues feeding into the aggregate
                                     shaper";
                            }

                        } // container rate

                        container avg-frame-overhead {
                            description "Enter the avg-frame-overhead context";

                            leaf overhead {
                                type decimal64 {
                                    fraction-digits 2;
                                }
                                units "percent";
                                description "Percentage average frame overhead";
                            }

                            leaf real-time {
                                type boolean;
                                description "Is it real-time?";
                            }

                        } // container avg-frame-overhead

                        container hw-agg-shaper-scheduler {
                            description "Enter the hw-agg-shaper-scheduler context";

                            leaf active {
                                type boolean;
                                description
                                    "The aggregate shaper is controlled by a
                                     hw-agg-shaper-scheduler";
                            }

                            leaf running {
                                type boolean;
                                description
                                    "The hw-agg-shaper-scheduler is currently running and
                                     updating the aggregate shaper rates";
                            }

                            leaf invalid-class-usage {
                                type boolean;
                                description
                                    "The aggregate shaper has queues in multiple classes in the
                                     same group in the hw-agg-shaper-scheduler";
                            }

                        } // container hw-agg-shaper-scheduler

                    } // container aggregate-shapers

                    container scheduler-policy {
                        description "Enter the scheduler-policy context";

                        list scheduler {
                            key "scheduler-name";
                            description "Enter the scheduler list instance";

                            leaf scheduler-name {
                                type types-sros:named-item;
                                description "Specifies the scheduler name.";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list scheduler

                    } // container scheduler-policy

                    list queue {
                        key "queue-id";
                        description "Enter the queue list instance";

                        leaf queue-id {
                            type leafref {
                                path "../../../../../../../qos/queue-group-templates/egress/queue-group[egress-queue-group-name=current()/../../queue-group-name]/queue/queue-id";
                            }
                            description "Specifies the queue overrides queue identifier.";
                        }

                        container statistics {
                            description "Enter the statistics context";

                            choice stat-mode {
                                case profile {

                                    container profile {
                                        description "Enter the profile context";

                                        leaf in-inplus-profile-forwarded-packets {
                                            type yang:counter64;
                                            description
                                                "The number of in-profile/in-plus-profile packets
                                                 (rate below CIR) forwarded.";
                                        }

                                        leaf in-inplus-profile-forwarded-octets {
                                            type yang:counter64;
                                            description
                                                "The number of in-profile/in-plus-profile octets
                                                 (rate below CIR) forwarded.";
                                        }

                                        leaf in-inplus-profile-dropped-packets {
                                            type yang:counter64;
                                            description
                                                "The number of in-profile/in-plus-profile packets
                                                 discarded.";
                                        }

                                        leaf in-inplus-profile-dropped-octets {
                                            type yang:counter64;
                                            description
                                                "The number of in-profile/in-plus-profile octets
                                                 discarded.";
                                        }

                                        leaf out-exceed-profile-forwarded-packets {
                                            type yang:counter64;
                                            description
                                                "The number of out-profile/exceed-profile packets
                                                 (rate above CIR) forwarded.";
                                        }

                                        leaf out-exceed-profile-forwarded-octets {
                                            type yang:counter64;
                                            description
                                                "The number of out-profile/exceed-profile octets
                                                 (rate above CIR) forwarded.";
                                        }

                                        leaf out-exceed-profile-dropped-packets {
                                            type yang:counter64;
                                            description
                                                "The number of out-profile/exceed-profile packets
                                                 discarded.";
                                        }

                                        leaf out-exceed-profile-dropped-octets {
                                            type yang:counter64;
                                            description
                                                "The number of out-profile/exceed-profile octets
                                                 discarded.";
                                        }

                                    } // container profile

                                }
                                case ecn-marked {

                                    container ecn-marked {
                                        description "Enter the ecn-marked context";

                                        leaf ecn-unmarked-forwarded-packets {
                                            type yang:counter64;
                                            description
                                                "The number of forwarded packets that were not ECN-marked
                                                 (CE codepoint not set).";
                                        }

                                        leaf ecn-unmarked-forwarded-octets {
                                            type yang:counter64;
                                            description
                                                "The number of forwarded octets that were not ECN-marked
                                                 (CE codepoint not set).";
                                        }

                                        leaf ecn-marked-forwarded-packets {
                                            type yang:counter64;
                                            description
                                                "The number of forwarded packets that were ECN-marked
                                                 (CE codepoint set).";
                                        }

                                        leaf ecn-marked-forwarded-octets {
                                            type yang:counter64;
                                            description
                                                "The number of forwarded octets that were ECN-marked
                                                 (CE codepoint set).";
                                        }

                                        leaf dropped-packets {
                                            type yang:counter64;
                                            description "The number of packets discarded.";
                                        }

                                        leaf dropped-octets {
                                            type yang:counter64;
                                            description "The number of octets discarded.";
                                        }

                                    } // container ecn-marked

                                }
                                case mismatch {

                                    container mismatch {
                                        description "Enter the mismatch context";

                                        leaf in-inplus-profile-forwarded-packets {
                                            type yang:counter64;
                                            description
                                                "The number of in-profile/in-plus-profile packets
                                                 (rate below CIR) forwarded.";
                                        }

                                        leaf in-inplus-profile-forwarded-octets {
                                            type yang:counter64;
                                            description
                                                "The number of in-profile/in-plus-profile octets
                                                 (rate below CIR) forwarded.";
                                        }

                                        leaf in-inplus-profile-dropped-packets {
                                            type yang:counter64;
                                            description
                                                "The number of in-profile/in-plus-profile packets
                                                 discarded.";
                                        }

                                        leaf in-inplus-profile-dropped-octets {
                                            type yang:counter64;
                                            description
                                                "The number of in-profile/in-plus-profile octets
                                                 discarded.";
                                        }

                                        leaf out-exceed-profile-forwarded-packets {
                                            type yang:counter64;
                                            description
                                                "The number of out-profile/exceed-profile packets
                                                 (rate above CIR) forwarded.";
                                        }

                                        leaf out-exceed-profile-forwarded-octets {
                                            type yang:counter64;
                                            description
                                                "The number of out-profile/exceed-profile octets
                                                 (rate above CIR) forwarded.";
                                        }

                                        leaf out-exceed-profile-dropped-packets {
                                            type yang:counter64;
                                            description
                                                "The number of out-profile/exceed-profile packets
                                                 discarded.";
                                        }

                                        leaf out-exceed-profile-dropped-octets {
                                            type yang:counter64;
                                            description
                                                "The number of out-profile/exceed-profile octets
                                                 discarded.";
                                        }

                                    } // container mismatch

                                }
                            }
                        } // container statistics

                        container hardware-queue {
                            description "Enter the hardware-queue context";

                            leaf adapted-admin-mbs {
                                type int64;
                                units "bytes";
                                description "Admin MBS.";
                            }

                            leaf exceed-droptail {
                                type types-qos:queue-burst-size-64-override-max;
                                description "Exceed droptail.";
                            }

                            leaf high-droptail {
                                type types-qos:queue-burst-size-64-override-max;
                                description "High droptail.";
                            }

                            leaf high-plus-droptail {
                                type union {
                                    type int64 {
                                        range "0..max";
                                    }
                                    type enumeration {
                                        enum auto                           { value -1; }
                                    }
                                }
                                description "Highplus droptail.";
                            }

                            leaf low-droptail {
                                type types-qos:queue-burst-size-64-override-max;
                                description "Low droptail.";
                            }

                            leaf operational-cbs {
                                type int64;
                                units "bytes";
                                description "Oper CBS.";
                            }

                            leaf operational-cir {
                                type types-qos:int-max;
                                description "Oper CIR.";
                            }

                            leaf operational-mbs {
                                type int64;
                                units "bytes";
                                description "Oper MBS.";
                            }

                            leaf operational-pir {
                                type types-qos:int-max;
                                description "Oper PIR.";
                            }

                            leaf burst-limit {
                                type union {
                                    type int32;
                                    type enumeration {
                                        enum auto                           { value -1; }
                                    }
                                }
                                description "Oper burst limit.";
                            }

                            leaf operational-exceed-burst {
                                type types-qos:int64-max;
                                description "Oper burst exceed.";
                            }

                            leaf operational-max-transmit-data-size {
                                type types-qos:int64-max;
                                description "Oper max transmit data size.";
                            }

                            leaf orphan {
                                type boolean;
                                description "Orphan queue";
                            }

                            leaf operational-burst-fir {
                                type types-qos:int64-max;
                                description "Oper burst FIR.";
                            }

                            container exceed-slope {
                                description "Enter the exceed-slope context";

                                leaf current-probability {
                                    type types-sros:percent;
                                    description "Specifies the current probability in percentage";
                                }

                            } // container exceed-slope

                            container high-slope {
                                description "Enter the high-slope context";

                                leaf current-probability {
                                    type types-sros:percent;
                                    description "Specifies the current probability in percentage";
                                }

                            } // container high-slope

                            container high-plus-slope {
                                description "Enter the high-plus-slope context";

                                leaf current-probability {
                                    type types-sros:percent;
                                    description "Specifies the current probability in percentage";
                                }

                            } // container high-plus-slope

                            container low-slope {
                                description "Enter the low-slope context";

                                leaf current-probability {
                                    type types-sros:percent;
                                    description "Specifies the current probability in percentage";
                                }

                            } // container low-slope

                        } // container hardware-queue

                        container queue-depth {
                            description "Enter the queue-depth context";

                            leaf elapsed-time {
                                type types-sros:time-interval;
                                description "Indicated the elapsed time.";
                            }

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                            leaf queue-polling-interval {
                                type types-sros:time-interval;
                                description "Indicates the queue polling interval.";
                            }

                            leaf last-violation {
                                type yang:date-and-time;
                                description "Indicates the last violation time.";
                            }

                            leaf total-threshold-violations {
                                type yang:counter32;
                                description "Indicates the total threshold violations.";
                            }

                            leaf high-water-mark-polling-interval {
                                type types-sros:time-duration;
                                units "microseconds";
                                description "Indicates the high water mark polling interval.";
                            }

                        } // container queue-depth

                    } // list queue

                } // list queue-group

                list virtual-port {
                    key "vport-name";
                    description "Enter the virtual-port list instance";

                    leaf vport-name {
                        type types-sros:named-item;
                        description "Specifies the name of the virtual port on the port.";
                    }

                    leaf multicast-hqos-adjustment-delta {
                        type uint32;
                        units "kilobps";
                        description "Indicates the actual bandwidth correction.";
                    }

                    container aggregate-rate {
                        description "Enter the aggregate-rate context";

                        container state {
                            description "Enter the state context";

                            leaf rate {
                                type types-qos:kbps;
                                units "kilobps";
                                description "Rate";
                            }

                            leaf limit-unused-bandwidth {
                                type boolean;
                                description "Aggregate rate limit-unused-bandwidth";
                            }

                            leaf on-the-wire {
                                type types-qos:on-the-wire;
                                description "On the wire";
                            }

                        } // container state

                    } // container aggregate-rate

                    container port-scheduler {
                        description "Enter the port-scheduler context";

                        leaf max-rate {
                            type types-qos:kbps;
                            units "kilobps";
                            description "Max rate";
                        }

                        leaf port-bandwidth {
                            type types-qos:kbps;
                            units "kilobps";
                            description "Port Bandwidth";
                        }

                        leaf consumed-rate {
                            type types-qos:kbps;
                            units "kilobps";
                            description "Consumed rate";
                        }

                        leaf offered-rate {
                            type types-qos:kbps;
                            units "kilobps";
                            description "Offered rate";
                        }

                        list group {
                            key "group-name";
                            description "Enter the group list instance";

                            leaf group-name {
                                type string;
                                description "Name";
                            }

                            container sched-hierarchy {
                                description "Enter the sched-hierarchy context";

                                list level {
                                    key "level-index";
                                    description "Enter the level list instance";

                                    leaf level-index {
                                        type int32 {
                                            range "0..8";
                                        }
                                    }

                                } // list level

                            } // container sched-hierarchy

                            container within-cir {
                                description "Enter the within-cir context";

                                leaf rate {
                                    type types-qos:kbps;
                                    units "kilobps";
                                    description "Rate";
                                }

                                leaf consumed {
                                    type types-qos:kbps;
                                    units "kilobps";
                                    description "Consumed";
                                }

                                leaf offered {
                                    type types-qos:kbps;
                                    units "kilobps";
                                    description "Offered";
                                }

                            } // container within-cir

                            container above-cir {
                                description "Enter the above-cir context";

                                leaf rate {
                                    type types-qos:kbps;
                                    units "kilobps";
                                    description "Rate";
                                }

                                leaf consumed {
                                    type types-qos:kbps;
                                    units "kilobps";
                                    description "Consumed";
                                }

                                leaf offered {
                                    type types-qos:kbps;
                                    units "kilobps";
                                    description "Offered";
                                }

                            } // container above-cir

                        } // list group

                        list level {
                            key "level-index";
                            description "Enter the level list instance";

                            leaf level-index {
                                type int32 {
                                    range "0..8";
                                }
                            }

                            container within-cir {
                                description "Enter the within-cir context";

                                leaf rate {
                                    type types-qos:kbps;
                                    units "kilobps";
                                    description "Rate";
                                }

                                leaf consumed {
                                    type types-qos:kbps;
                                    units "kilobps";
                                    description "Consumed";
                                }

                                leaf offered {
                                    type types-qos:kbps;
                                    units "kilobps";
                                    description "Offered";
                                }

                                container sched-hierarchy {
                                    description "Enter the sched-hierarchy context";

                                    container queue {
                                        description "Enter the queue context";

                                        container port-queue-group {
                                            description "Enter the port-queue-group context";

                                            list queue {
                                                key "member";
                                                description "Enter the queue list instance";

                                                leaf member {
                                                    type uint32;
                                                    description "Member information";
                                                }

                                                leaf queue-id {
                                                    type int32;
                                                    description "Queue identifier";
                                                }

                                                leaf port {
                                                    type types-sros:port;
                                                    description "Port identifier";
                                                }

                                                leaf port-mode {
                                                    type enumeration {
                                                        enum access                         { value 1; }
                                                        enum network                        { value 2; }
                                                    }
                                                    description "Port mode";
                                                }

                                                leaf queue-group-template {
                                                    type string;
                                                    description "Queue group template";
                                                }

                                                leaf queue-group-instance {
                                                    type int32;
                                                    description "Queue group instance";
                                                }

                                            } // list queue

                                        } // container port-queue-group

                                        container sap {
                                            description "Enter the sap context";

                                            list queue {
                                                key "member";
                                                description "Enter the queue list instance";

                                                leaf member {
                                                    type uint32;
                                                    description "Member information";
                                                }

                                                leaf queue-id {
                                                    type int32;
                                                    description "Queue identifier";
                                                }

                                                leaf sap-id {
                                                    type types-sros:sap;
                                                    description "SAP identifier";
                                                }

                                                leaf port {
                                                    type types-sros:port;
                                                    description "Port identifier";
                                                }

                                            } // list queue

                                        } // container sap

                                        container sla-profile-instance {
                                            description "Enter the sla-profile-instance context";

                                            list queue {
                                                key "member";
                                                description "Enter the queue list instance";

                                                leaf member {
                                                    type uint32;
                                                    description "Member information";
                                                }

                                                leaf queue-id {
                                                    type int32;
                                                    description "Queue identifier";
                                                }

                                                leaf subscriber-id {
                                                    type types-submgt:subscriber-id;
                                                    description "Subscriber Identification string";
                                                }

                                                leaf sla-profile-instance-id {
                                                    type types-submgt:sla-profile-instance-id;
                                                    description "SLA profile instance Identification string";
                                                }

                                                leaf fp {
                                                    type int32;
                                                    description "FP number";
                                                }

                                            } // list queue

                                        } // container sla-profile-instance

                                    } // container queue

                                    container scheduler {
                                        description "Enter the scheduler context";

                                        container sap {
                                            description "Enter the sap context";

                                            list scheduler {
                                                key "member";
                                                description "Enter the scheduler list instance";

                                                leaf member {
                                                    type uint32;
                                                    description "Member information";
                                                }

                                                leaf scheduler-name {
                                                    type string;
                                                    description "Name";
                                                }

                                                leaf sap-id {
                                                    type types-sros:sap;
                                                    description "SAP identifier";
                                                }

                                            } // list scheduler

                                        } // container sap

                                        container subscriber {
                                            description "Enter the subscriber context";

                                            list scheduler {
                                                key "member";
                                                description "Enter the scheduler list instance";

                                                leaf member {
                                                    type uint32;
                                                    description "Member information";
                                                }

                                                leaf scheduler-name {
                                                    type string;
                                                    description "Name";
                                                }

                                                leaf subscriber-id {
                                                    type types-submgt:subscriber-id;
                                                    description "Subscriber Identification string";
                                                }

                                            } // list scheduler

                                        } // container subscriber

                                        container sla-profile-instance {
                                            description "Enter the sla-profile-instance context";

                                            list scheduler {
                                                key "member";
                                                description "Enter the scheduler list instance";

                                                leaf member {
                                                    type uint32;
                                                    description "Member information";
                                                }

                                                leaf scheduler-name {
                                                    type string;
                                                    description "Name";
                                                }

                                                leaf subscriber-id {
                                                    type types-submgt:subscriber-id;
                                                    description "Subscriber Identification string";
                                                }

                                                leaf sla-profile-instance-id {
                                                    type types-submgt:sla-profile-instance-id;
                                                    description "SLA profile instance Identification string";
                                                }

                                            } // list scheduler

                                            list t0-scheduler {
                                                key "member";
                                                description "Enter the t0-scheduler list instance";

                                                leaf member {
                                                    type uint32;
                                                    description "Member information";
                                                }

                                                leaf scheduler-name {
                                                    type string;
                                                    description "Name";
                                                }

                                                leaf subscriber-id {
                                                    type types-submgt:subscriber-id;
                                                    description "Subscriber Identification string";
                                                }

                                                leaf sla-profile-instance-id {
                                                    type types-submgt:sla-profile-instance-id;
                                                    description "SLA profile instance Identification string";
                                                }

                                            } // list t0-scheduler

                                        } // container sla-profile-instance

                                    } // container scheduler

                                } // container sched-hierarchy

                            } // container within-cir

                            container above-cir {
                                description "Enter the above-cir context";

                                leaf rate {
                                    type types-qos:kbps;
                                    units "kilobps";
                                    description "Rate";
                                }

                                leaf consumed {
                                    type types-qos:kbps;
                                    units "kilobps";
                                    description "Consumed";
                                }

                                leaf offered {
                                    type types-qos:kbps;
                                    units "kilobps";
                                    description "Offered";
                                }

                                container sched-hierarchy {
                                    description "Enter the sched-hierarchy context";

                                    container queue {
                                        description "Enter the queue context";

                                        container port-queue-group {
                                            description "Enter the port-queue-group context";

                                            list queue {
                                                key "member";
                                                description "Enter the queue list instance";

                                                leaf member {
                                                    type uint32;
                                                    description "Member information";
                                                }

                                                leaf queue-id {
                                                    type int32;
                                                    description "Queue identifier";
                                                }

                                                leaf port {
                                                    type types-sros:port;
                                                    description "Port identifier";
                                                }

                                                leaf port-mode {
                                                    type enumeration {
                                                        enum access                         { value 1; }
                                                        enum network                        { value 2; }
                                                    }
                                                    description "Port mode";
                                                }

                                                leaf queue-group-template {
                                                    type string;
                                                    description "Queue group template";
                                                }

                                                leaf queue-group-instance {
                                                    type int32;
                                                    description "Queue group instance";
                                                }

                                            } // list queue

                                        } // container port-queue-group

                                        container sap {
                                            description "Enter the sap context";

                                            list queue {
                                                key "member";
                                                description "Enter the queue list instance";

                                                leaf member {
                                                    type uint32;
                                                    description "Member information";
                                                }

                                                leaf queue-id {
                                                    type int32;
                                                    description "Queue identifier";
                                                }

                                                leaf sap-id {
                                                    type types-sros:sap;
                                                    description "SAP identifier";
                                                }

                                                leaf port {
                                                    type types-sros:port;
                                                    description "Port identifier";
                                                }

                                            } // list queue

                                        } // container sap

                                        container sla-profile-instance {
                                            description "Enter the sla-profile-instance context";

                                            list queue {
                                                key "member";
                                                description "Enter the queue list instance";

                                                leaf member {
                                                    type uint32;
                                                    description "Member information";
                                                }

                                                leaf queue-id {
                                                    type int32;
                                                    description "Queue identifier";
                                                }

                                                leaf subscriber-id {
                                                    type types-submgt:subscriber-id;
                                                    description "Subscriber Identification string";
                                                }

                                                leaf sla-profile-instance-id {
                                                    type types-submgt:sla-profile-instance-id;
                                                    description "SLA profile instance Identification string";
                                                }

                                                leaf fp {
                                                    type int32;
                                                    description "FP number";
                                                }

                                            } // list queue

                                        } // container sla-profile-instance

                                    } // container queue

                                    container scheduler {
                                        description "Enter the scheduler context";

                                        container sap {
                                            description "Enter the sap context";

                                            list scheduler {
                                                key "member";
                                                description "Enter the scheduler list instance";

                                                leaf member {
                                                    type uint32;
                                                    description "Member information";
                                                }

                                                leaf scheduler-name {
                                                    type string;
                                                    description "Name";
                                                }

                                                leaf sap-id {
                                                    type types-sros:sap;
                                                    description "SAP identifier";
                                                }

                                            } // list scheduler

                                        } // container sap

                                        container subscriber {
                                            description "Enter the subscriber context";

                                            list scheduler {
                                                key "member";
                                                description "Enter the scheduler list instance";

                                                leaf member {
                                                    type uint32;
                                                    description "Member information";
                                                }

                                                leaf scheduler-name {
                                                    type string;
                                                    description "Name";
                                                }

                                                leaf subscriber-id {
                                                    type types-submgt:subscriber-id;
                                                    description "Subscriber Identification string";
                                                }

                                            } // list scheduler

                                        } // container subscriber

                                        container sla-profile-instance {
                                            description "Enter the sla-profile-instance context";

                                            list scheduler {
                                                key "member";
                                                description "Enter the scheduler list instance";

                                                leaf member {
                                                    type uint32;
                                                    description "Member information";
                                                }

                                                leaf scheduler-name {
                                                    type string;
                                                    description "Name";
                                                }

                                                leaf subscriber-id {
                                                    type types-submgt:subscriber-id;
                                                    description "Subscriber Identification string";
                                                }

                                                leaf sla-profile-instance-id {
                                                    type types-submgt:sla-profile-instance-id;
                                                    description "SLA profile instance Identification string";
                                                }

                                            } // list scheduler

                                            list t0-scheduler {
                                                key "member";
                                                description "Enter the t0-scheduler list instance";

                                                leaf member {
                                                    type uint32;
                                                    description "Member information";
                                                }

                                                leaf scheduler-name {
                                                    type string;
                                                    description "Name";
                                                }

                                                leaf subscriber-id {
                                                    type types-submgt:subscriber-id;
                                                    description "Subscriber Identification string";
                                                }

                                                leaf sla-profile-instance-id {
                                                    type types-submgt:sla-profile-instance-id;
                                                    description "SLA profile instance Identification string";
                                                }

                                            } // list t0-scheduler

                                        } // container sla-profile-instance

                                    } // container scheduler

                                } // container sched-hierarchy

                            } // container above-cir

                        } // list level

                        container statistics {
                            description "Enter the statistics context";

                            leaf total-forwarded-octets {
                                type yang:counter64;
                                description "Indicates the total number of octets forwarded.";
                            }

                            leaf total-forwarded-packets {
                                type yang:counter64;
                                description "Indicates the total number of packets forwarded.";
                            }

                            leaf total-dropped-octets {
                                type yang:counter64;
                                description "Indicates the total number of octets dropped.";
                            }

                            leaf total-dropped-packets {
                                type yang:counter64;
                                description "Indicates the total number of packets dropped.";
                            }

                            leaf last-cleared-time {
                                type yang:date-and-time;
                                description
                                    "Indicates the time, since system startup, when the counters in
                                     IF-MIB::ifTable were last cleared.";
                            }

                            list level {
                                key "priority-level";
                                description "Enter the level list instance";

                                leaf priority-level {
                                    type uint32 {
                                        range "1..8";
                                    }
                                    description "Specifies the scheduler level of the port scheduler policy.";
                                }

                                leaf forwarded-octets {
                                    type yang:counter64;
                                    description "Indicates the total number of octets forwarded.";
                                }

                                leaf forwarded-packets {
                                    type yang:counter64;
                                    description "Indicates the total number of packets forwarded.";
                                }

                                leaf dropped-octets {
                                    type yang:counter64;
                                    description "Indicates the total number of octets dropped.";
                                }

                                leaf dropped-packets {
                                    type yang:counter64;
                                    description "Indicates the total number of packets dropped.";
                                }

                            } // list level

                        } // container statistics

                        container monitor-threshold {
                            description "Enter the monitor-threshold context";

                            leaf exceed-count {
                                type yang:counter32;
                                description "Indicates the exceed count for egress port scheduler.";
                            }

                            leaf start-time {
                                type yang:date-and-time;
                                description "Indicates the start time for threshold monitoring.";
                            }

                            leaf end-time {
                                type yang:date-and-time;
                                description "Indicates the end time for threshold monitoring.";
                            }

                            leaf total-samples {
                                type yang:counter32;
                                description "Indicates the total samples collected during the threshold monitoring interval.";
                            }

                            list level {
                                key "priority-level";
                                description "Enter the level list instance";

                                leaf priority-level {
                                    type uint32 {
                                        range "1..8";
                                    }
                                    description "Specifies the scheduler level of the port scheduler policy.";
                                }

                                leaf exceed-count {
                                    type yang:counter32;
                                    description "Indicates the exceed count for egress port scheduler.";
                                }

                            } // list level

                            list group {
                                key "group-name";
                                description "Enter the group list instance";

                                leaf group-name {
                                    type types-sros:named-item;
                                    description "Port scheduler policy group.";
                                }

                                leaf exceed-count {
                                    type yang:counter32;
                                    description "Indicates the exceed count for egress port scheduler.";
                                }

                            } // list group

                        } // container monitor-threshold

                    } // container port-scheduler

                    container scheduler-policy {
                        description "Enter the scheduler-policy context";

                        list scheduler {
                            key "scheduler-name";
                            description "Enter the scheduler list instance";

                            leaf scheduler-name {
                                type types-sros:named-item;
                                description "Specifies the scheduler name.";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                            container qos-scheduler {
                                description "Enter the qos-scheduler context";

                                leaf members {
                                    type uint32;
                                    description "Members";
                                }

                                leaf max-pir {
                                    type types-qos:sched-pir;
                                    description "Max PIR rate";
                                }

                                leaf oper-pir {
                                    type types-qos:sched-pir;
                                    description "Operational PIR rate";
                                }

                                leaf parent-limit-unused-bandwidth {
                                    type boolean;
                                    description "Parent limit unused bandwidth";
                                }

                                leaf orphan {
                                    type boolean;
                                    description "Orphan";
                                }

                                list level {
                                    key "level-index";
                                    description "Enter the level list instance";

                                    leaf level-index {
                                        type int32 {
                                            range "0..8";
                                        }
                                    }

                                    container within-cir {
                                        description "Enter the within-cir context";

                                        leaf members {
                                            type uint32;
                                            description "Members";
                                        }

                                        leaf consumed {
                                            type types-qos:kbps;
                                            units "kilobps";
                                            description "Consumed";
                                        }

                                        leaf offered {
                                            type types-qos:kbps;
                                            units "kilobps";
                                            description "Offered";
                                        }

                                        container sched-hierarchy {
                                            description "Enter the sched-hierarchy context";

                                            container queue {
                                                description "Enter the queue context";

                                                container port-queue-group {
                                                    description "Enter the port-queue-group context";

                                                    list queue {
                                                        key "member";
                                                        description "Enter the queue list instance";

                                                        leaf member {
                                                            type uint32;
                                                            description "Member information";
                                                        }

                                                        leaf queue-id {
                                                            type int32;
                                                            description "Queue identifier";
                                                        }

                                                        leaf port {
                                                            type types-sros:port;
                                                            description "Port identifier";
                                                        }

                                                        leaf port-mode {
                                                            type enumeration {
                                                                enum access                         { value 1; }
                                                                enum network                        { value 2; }
                                                            }
                                                            description "Port mode";
                                                        }

                                                        leaf queue-group-template {
                                                            type string;
                                                            description "Queue group template";
                                                        }

                                                        leaf queue-group-instance {
                                                            type int32;
                                                            description "Queue group instance";
                                                        }

                                                    } // list queue

                                                } // container port-queue-group

                                                container sap {
                                                    description "Enter the sap context";

                                                    list queue {
                                                        key "member";
                                                        description "Enter the queue list instance";

                                                        leaf member {
                                                            type uint32;
                                                            description "Member information";
                                                        }

                                                        leaf queue-id {
                                                            type int32;
                                                            description "Queue identifier";
                                                        }

                                                        leaf sap-id {
                                                            type types-sros:sap;
                                                            description "SAP identifier";
                                                        }

                                                        leaf port {
                                                            type types-sros:port;
                                                            description "Port identifier";
                                                        }

                                                    } // list queue

                                                } // container sap

                                            } // container queue

                                            container scheduler {
                                                description "Enter the scheduler context";

                                                container sap {
                                                    description "Enter the sap context";

                                                    list scheduler {
                                                        key "member";
                                                        description "Enter the scheduler list instance";

                                                        leaf member {
                                                            type uint32;
                                                            description "Member information";
                                                        }

                                                        leaf scheduler-name {
                                                            type string;
                                                            description "Name";
                                                        }

                                                        leaf sap-id {
                                                            type types-sros:sap;
                                                            description "SAP identifier";
                                                        }

                                                    } // list scheduler

                                                } // container sap

                                                container vport {
                                                    description "Enter the vport context";

                                                    list scheduler {
                                                        key "member";
                                                        description "Enter the scheduler list instance";

                                                        leaf member {
                                                            type uint32;
                                                            description "Member information";
                                                        }

                                                        leaf scheduler-name {
                                                            type string;
                                                            description "Name";
                                                        }

                                                        leaf vport-name {
                                                            type types-sros:named-item-or-empty;
                                                            description "Virtual port name";
                                                        }

                                                    } // list scheduler

                                                } // container vport

                                                container subscriber {
                                                    description "Enter the subscriber context";

                                                    list scheduler {
                                                        key "member";
                                                        description "Enter the scheduler list instance";

                                                        leaf member {
                                                            type uint32;
                                                            description "Member information";
                                                        }

                                                        leaf scheduler-name {
                                                            type string;
                                                            description "Name";
                                                        }

                                                        leaf subscriber-id {
                                                            type types-submgt:subscriber-id;
                                                            description "Subscriber Identification string";
                                                        }

                                                    } // list scheduler

                                                } // container subscriber

                                                container sla-profile-instance {
                                                    description "Enter the sla-profile-instance context";

                                                    list scheduler {
                                                        key "member";
                                                        description "Enter the scheduler list instance";

                                                        leaf member {
                                                            type uint32;
                                                            description "Member information";
                                                        }

                                                        leaf scheduler-name {
                                                            type string;
                                                            description "Name";
                                                        }

                                                        leaf subscriber-id {
                                                            type types-submgt:subscriber-id;
                                                            description "Subscriber Identification string";
                                                        }

                                                        leaf sla-profile-instance-id {
                                                            type types-submgt:sla-profile-instance-id;
                                                            description "SLA profile instance Identification string";
                                                        }

                                                    } // list scheduler

                                                } // container sla-profile-instance

                                            } // container scheduler

                                        } // container sched-hierarchy

                                    } // container within-cir

                                    container above-cir {
                                        description "Enter the above-cir context";

                                        leaf members {
                                            type uint32;
                                            description "Members";
                                        }

                                        leaf consumed {
                                            type types-qos:kbps;
                                            units "kilobps";
                                            description "Consumed";
                                        }

                                        leaf offered {
                                            type types-qos:kbps;
                                            units "kilobps";
                                            description "Offered";
                                        }

                                        container sched-hierarchy {
                                            description "Enter the sched-hierarchy context";

                                            container queue {
                                                description "Enter the queue context";

                                                container port-queue-group {
                                                    description "Enter the port-queue-group context";

                                                    list queue {
                                                        key "member";
                                                        description "Enter the queue list instance";

                                                        leaf member {
                                                            type uint32;
                                                            description "Member information";
                                                        }

                                                        leaf queue-id {
                                                            type int32;
                                                            description "Queue identifier";
                                                        }

                                                        leaf port {
                                                            type types-sros:port;
                                                            description "Port identifier";
                                                        }

                                                        leaf port-mode {
                                                            type enumeration {
                                                                enum access                         { value 1; }
                                                                enum network                        { value 2; }
                                                            }
                                                            description "Port mode";
                                                        }

                                                        leaf queue-group-template {
                                                            type string;
                                                            description "Queue group template";
                                                        }

                                                        leaf queue-group-instance {
                                                            type int32;
                                                            description "Queue group instance";
                                                        }

                                                    } // list queue

                                                } // container port-queue-group

                                                container sap {
                                                    description "Enter the sap context";

                                                    list queue {
                                                        key "member";
                                                        description "Enter the queue list instance";

                                                        leaf member {
                                                            type uint32;
                                                            description "Member information";
                                                        }

                                                        leaf queue-id {
                                                            type int32;
                                                            description "Queue identifier";
                                                        }

                                                        leaf sap-id {
                                                            type types-sros:sap;
                                                            description "SAP identifier";
                                                        }

                                                        leaf port {
                                                            type types-sros:port;
                                                            description "Port identifier";
                                                        }

                                                    } // list queue

                                                } // container sap

                                            } // container queue

                                            container scheduler {
                                                description "Enter the scheduler context";

                                                container sap {
                                                    description "Enter the sap context";

                                                    list scheduler {
                                                        key "member";
                                                        description "Enter the scheduler list instance";

                                                        leaf member {
                                                            type uint32;
                                                            description "Member information";
                                                        }

                                                        leaf scheduler-name {
                                                            type string;
                                                            description "Name";
                                                        }

                                                        leaf sap-id {
                                                            type types-sros:sap;
                                                            description "SAP identifier";
                                                        }

                                                    } // list scheduler

                                                } // container sap

                                                container vport {
                                                    description "Enter the vport context";

                                                    list scheduler {
                                                        key "member";
                                                        description "Enter the scheduler list instance";

                                                        leaf member {
                                                            type uint32;
                                                            description "Member information";
                                                        }

                                                        leaf scheduler-name {
                                                            type string;
                                                            description "Name";
                                                        }

                                                        leaf vport-name {
                                                            type types-sros:named-item-or-empty;
                                                            description "Virtual port name";
                                                        }

                                                    } // list scheduler

                                                } // container vport

                                                container subscriber {
                                                    description "Enter the subscriber context";

                                                    list scheduler {
                                                        key "member";
                                                        description "Enter the scheduler list instance";

                                                        leaf member {
                                                            type uint32;
                                                            description "Member information";
                                                        }

                                                        leaf scheduler-name {
                                                            type string;
                                                            description "Name";
                                                        }

                                                        leaf subscriber-id {
                                                            type types-submgt:subscriber-id;
                                                            description "Subscriber Identification string";
                                                        }

                                                    } // list scheduler

                                                } // container subscriber

                                                container sla-profile-instance {
                                                    description "Enter the sla-profile-instance context";

                                                    list scheduler {
                                                        key "member";
                                                        description "Enter the scheduler list instance";

                                                        leaf member {
                                                            type uint32;
                                                            description "Member information";
                                                        }

                                                        leaf scheduler-name {
                                                            type string;
                                                            description "Name";
                                                        }

                                                        leaf subscriber-id {
                                                            type types-submgt:subscriber-id;
                                                            description "Subscriber Identification string";
                                                        }

                                                        leaf sla-profile-instance-id {
                                                            type types-submgt:sla-profile-instance-id;
                                                            description "SLA profile instance Identification string";
                                                        }

                                                    } // list scheduler

                                                } // container sla-profile-instance

                                            } // container scheduler

                                        } // container sched-hierarchy

                                    } // container above-cir

                                } // list level

                            } // container qos-scheduler

                        } // list scheduler

                    } // container scheduler-policy

                    container hw-agg-shaper-scheduler {
                        description "Enter the hw-agg-shaper-scheduler context";

                        leaf policy-name {
                            type types-sros:named-item-or-empty;
                            description "Specifies an hardware aggregate shaper scheduler policy.";
                        }

                        leaf oper-color {
                            type types-qos:color-oper;
                            description "Specify what is state of hw-agg-shaper scheduler algorithm";
                        }

                        leaf num-child-agg-shapers {
                            type int64 {
                                range "0..6400000000";
                            }
                            description "Specify number of agg-shapers parented to this vport scheduler.";
                        }

                        leaf num-orphan-agg-shapers {
                            type int64 {
                                range "0..6400000000";
                            }
                            description "Specify number of agg-shapers not parented to this vport scheduler.";
                        }

                        container statistics {
                            description "Enter the statistics context";

                            leaf total-forwarded-octets {
                                type yang:counter64;
                                description "Indicates the total number of octets forwarded.";
                            }

                            leaf total-forwarded-packets {
                                type yang:counter64;
                                description "Indicates the total number of packets forwarded.";
                            }

                            leaf total-dropped-octets {
                                type yang:counter64;
                                description "Indicates the total number of octets dropped.";
                            }

                            leaf total-dropped-packets {
                                type yang:counter64;
                                description "Indicates the total number of packets dropped.";
                            }

                            leaf last-cleared-time {
                                type yang:date-and-time;
                                description
                                    "Indicates the time, since system startup, when the counters in
                                     IF-MIB::ifTable were last cleared.";
                            }

                            list class {
                                key "sched-class";
                                description "Enter the class list instance";

                                leaf sched-class {
                                    type uint32 {
                                        range "1..6";
                                    }
                                    description "Specifies the scheduler class of the hardware aggregate shaper scheduler policy.";
                                }

                                leaf forwarded-octets {
                                    type yang:counter64;
                                    description "Indicates the total number of octets forwarded.";
                                }

                                leaf forwarded-packets {
                                    type yang:counter64;
                                    description "Indicates the total number of packets forwarded.";
                                }

                                leaf dropped-octets {
                                    type yang:counter64;
                                    description "Indicates the total number of octets dropped.";
                                }

                                leaf dropped-packets {
                                    type yang:counter64;
                                    description "Indicates the total number of packets dropped.";
                                }

                                leaf last-cleared-time {
                                    type yang:date-and-time;
                                    description
                                        "Indicates the time, since system startup, when the counters in
                                         IF-MIB::ifTable were last cleared.";
                                }

                            } // list class

                        } // container statistics

                        container monitor-threshold {
                            description "Enter the monitor-threshold context";

                            leaf exceed-count {
                                type yang:counter32;
                                description "Indicates the exceed count for egress hardware aggregate shaper scheduler.";
                            }

                            leaf start-time {
                                type yang:date-and-time;
                                description "Indicates the start time for threshold monitoring.";
                            }

                            leaf end-time {
                                type yang:date-and-time;
                                description "Indicates the end time for threshold monitoring.";
                            }

                            leaf total-samples {
                                type yang:counter32;
                                description "Indicates the total samples collected during the threshold monitoring interval.";
                            }

                        } // container monitor-threshold

                    } // container hw-agg-shaper-scheduler

                } // list virtual-port

            } // container egress

            container ingress {
                description "Enter the ingress context";

                list queue-group {
                    key "queue-group-name";
                    description "Enter the queue-group list instance";

                    leaf queue-group-name {
                        type leafref {
                            path "../../../../../../qos/queue-group-templates/ingress/queue-group/ingress-queue-group-name";
                        }
                        description "Specifies the queue-group name.";
                    }

                    container scheduler-policy {
                        description "Enter the scheduler-policy context";

                        list scheduler {
                            key "scheduler-name";
                            description "Enter the scheduler list instance";

                            leaf scheduler-name {
                                type types-sros:named-item;
                                description "Specifies the scheduler name.";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list scheduler

                    } // container scheduler-policy

                    list queue {
                        key "queue-id";
                        description "Enter the queue list instance";

                        leaf queue-id {
                            type types-qos:ingress-queue-id;
                            description "Specifies the queue group queue identifier.";
                        }

                        container statistics {
                            description "Enter the statistics context";

                            choice stat-mode {
                                case unicast-priority {

                                    container unicast-priority {
                                        description "Enter the unicast-priority context";

                                        leaf high-priority-offered-packets {
                                            type yang:counter64;
                                            description "The number of high-priority packets offered by packet processor to traffic manager.";
                                        }

                                        leaf high-priority-offered-octets {
                                            type yang:counter64;
                                            description "The number of high-priority octets offered by packet processor to traffic manager.";
                                        }

                                        leaf low-priority-offered-packets {
                                            type yang:counter64;
                                            description "The number of low-priority packets offered by packet processor to traffic manager.";
                                        }

                                        leaf low-priority-offered-octets {
                                            type yang:counter64;
                                            description "The number of low-priority octets offered by packet processor to traffic manager.";
                                        }

                                        leaf high-priority-dropped-packets {
                                            type yang:counter64;
                                            description "The number of high-priority packets dropped by packet processor to traffic manager.";
                                        }

                                        leaf high-priority-dropped-octets {
                                            type yang:counter64;
                                            description "The number of high-priority octets dropped by packet processor to traffic manager.";
                                        }

                                        leaf low-priority-dropped-packets {
                                            type yang:counter64;
                                            description "The number of low-priority packets dropped by packet processor to traffic manager.";
                                        }

                                        leaf low-priority-dropped-octets {
                                            type yang:counter64;
                                            description "The number of low-priority octets dropped by packet processor to traffic manager.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container unicast-priority

                                }
                                case unicast-profile {

                                    container unicast-profile {
                                        description "Enter the unicast-profile context";

                                        leaf color-in-offered-packets {
                                            type yang:counter64;
                                            description "The number of color-in packets offered to traffic manager.";
                                        }

                                        leaf color-in-offered-octets {
                                            type yang:counter64;
                                            description "The number of color-in octets offered to traffic manager.";
                                        }

                                        leaf color-out-offered-packets {
                                            type yang:counter64;
                                            description "The number of color-out packets offered to traffic manager.";
                                        }

                                        leaf color-out-offered-octets {
                                            type yang:counter64;
                                            description "The number of color-out octets offered to traffic manager.";
                                        }

                                        leaf color-offered-packets {
                                            type yang:counter64;
                                            description "The number of color packets offered to traffic manager.";
                                        }

                                        leaf color-offered-octets {
                                            type yang:counter64;
                                            description "The number of color octets offered to traffic manager.";
                                        }

                                        leaf uncolor-offered-packets {
                                            type yang:counter64;
                                            description "The number of uncolor packets offered to traffic manager.";
                                        }

                                        leaf uncolor-offered-octets {
                                            type yang:counter64;
                                            description "The number of uncolor octets offered to traffic manager.";
                                        }

                                        leaf color-out-dropped-packets {
                                            type yang:counter64;
                                            description "The number of color-out packets dropped.";
                                        }

                                        leaf color-out-dropped-octets {
                                            type yang:counter64;
                                            description "The number of color-out octets dropped.";
                                        }

                                        leaf color-in-uncolor-dropped-packets {
                                            type yang:counter64;
                                            description "The number of color-in/uncolor packets dropped.";
                                        }

                                        leaf color-in-uncolor-dropped-octets {
                                            type yang:counter64;
                                            description "The number of color-in/uncolor octets dropped.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container unicast-profile

                                }
                                case multipoint-priority {

                                    container multipoint-priority {
                                        description "Enter the multipoint-priority context";

                                        leaf high-priority-offered-packets {
                                            type yang:counter64;
                                            description "The number of high-priority packets offered by packet processor to traffic manager.";
                                        }

                                        leaf high-priority-offered-octets {
                                            type yang:counter64;
                                            description "The number of high-priority octets offered by packet processor to traffic manager.";
                                        }

                                        leaf low-priority-offered-packets {
                                            type yang:counter64;
                                            description "The number of low-priority packets offered by packet processor to traffic manager.";
                                        }

                                        leaf low-priority-offered-octets {
                                            type yang:counter64;
                                            description "The number of low-priority octets offered by packet processor to traffic manager.";
                                        }

                                        leaf combined-offered-packets {
                                            type yang:counter64;
                                            description "The number of combined high and low priority packets offered by packet processor to traffic manager.";
                                        }

                                        leaf combined-offered-octets {
                                            type yang:counter64;
                                            description "The number of combined high and low priority octets offered by packet processor to traffic manager.";
                                        }

                                        leaf managed-offered-packets {
                                            type yang:counter64;
                                            description "The number of managed packets offered by packet processor to traffic manager.";
                                        }

                                        leaf managed-offered-octets {
                                            type yang:counter64;
                                            description "The number of managed octets offered by packet processor to traffic manager.";
                                        }

                                        leaf high-priority-dropped-packets {
                                            type yang:counter64;
                                            description "The number of high-priority packets dropped by packet processor to traffic manager.";
                                        }

                                        leaf high-priority-dropped-octets {
                                            type yang:counter64;
                                            description "The number of high-priority octets dropped by packet processor to traffic manager.";
                                        }

                                        leaf low-priority-dropped-packets {
                                            type yang:counter64;
                                            description "The number of low-priority packets dropped by packet processor to traffic manager.";
                                        }

                                        leaf low-priority-dropped-octets {
                                            type yang:counter64;
                                            description "The number of low-priority octets dropped by packet processor to traffic manager.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container multipoint-priority

                                }
                                case multipoint-profile {

                                    container multipoint-profile {
                                        description "Enter the multipoint-profile context";

                                        leaf color-in-offered-packets {
                                            type yang:counter64;
                                            description "The number of color-in packets offered to traffic manager.";
                                        }

                                        leaf color-in-offered-octets {
                                            type yang:counter64;
                                            description "The number of color-in octets offered to traffic manager.";
                                        }

                                        leaf color-out-offered-packets {
                                            type yang:counter64;
                                            description "The number of color-out packets offered to traffic manager.";
                                        }

                                        leaf color-out-offered-octets {
                                            type yang:counter64;
                                            description "The number of color-out octets offered to traffic manager.";
                                        }

                                        leaf uncolor-offered-packets {
                                            type yang:counter64;
                                            description "The number of uncolor packets offered to traffic manager.";
                                        }

                                        leaf uncolor-offered-octets {
                                            type yang:counter64;
                                            description "The number of uncolor octets offered to traffic manager.";
                                        }

                                        leaf combined-offered-packets {
                                            type yang:counter64;
                                            description "The number of combined colored in, out and uncolored packets offered to traffic manager.";
                                        }

                                        leaf combined-offered-octets {
                                            type yang:counter64;
                                            description "The number of combined colored in, out and uncolored octets offered to traffic manager.";
                                        }

                                        leaf managed-offered-packets {
                                            type yang:counter64;
                                            description "The number of managed packets offered by packet processor to traffic manager.";
                                        }

                                        leaf managed-offered-octets {
                                            type yang:counter64;
                                            description "The number of managed octets offered by packet processor to traffic manager.";
                                        }

                                        leaf color-out-dropped-packets {
                                            type yang:counter64;
                                            description "The number of color-out packets dropped.";
                                        }

                                        leaf color-out-dropped-octets {
                                            type yang:counter64;
                                            description "The number of color-out octets dropped.";
                                        }

                                        leaf color-in-uncolor-dropped-packets {
                                            type yang:counter64;
                                            description "The number of color-in/uncolor packets dropped.";
                                        }

                                        leaf color-in-uncolor-dropped-octets {
                                            type yang:counter64;
                                            description "The number of color-in/uncolor octets dropped.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container multipoint-profile

                                }
                            }
                        } // container statistics

                        container queue-depth {
                            description "Enter the queue-depth context";

                            leaf elapsed-time {
                                type types-sros:time-interval;
                                description "Indicated the elapsed time.";
                            }

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                            leaf queue-polling-interval {
                                type types-sros:time-interval;
                                description "Indicates the queue polling interval.";
                            }

                        } // container queue-depth

                        list hardware-queue {
                            key "source-tap-offset dest-card dest-fp dest-tap-offset";
                            description "Enter the hardware-queue list instance";

                            leaf source-tap-offset {
                                type int32;
                                description "Source TAP.";
                            }

                            leaf dest-card {
                                type int32;
                                description "Card number";
                            }

                            leaf dest-fp {
                                type int32;
                                description "FP number";
                            }

                            leaf dest-tap-offset {
                                type int32;
                                description "Destination TAP.";
                            }

                            leaf adapted-admin-mbs {
                                type int64;
                                units "bytes";
                                description "Admin MBS.";
                            }

                            leaf adapted-admin-cbs {
                                type int64;
                                units "bytes";
                                description "Admin CBS.";
                            }

                            leaf operational-mbs {
                                type int64;
                                units "bytes";
                                description "Oper MBS.";
                            }

                            leaf depth {
                                type union {
                                    type enumeration {
                                        enum max                            { value -1; }
                                    }
                                    type int64;
                                }
                                description "Depth CIR.";
                            }

                            leaf operational-cir {
                                type union {
                                    type enumeration {
                                        enum max                            { value -1; }
                                    }
                                    type int64;
                                }
                                description "Oper CIR.";
                            }

                            leaf operational-fir {
                                type union {
                                    type enumeration {
                                        enum max                            { value -1; }
                                    }
                                    type int64;
                                }
                                description "Oper FIR.";
                            }

                            leaf operational-pir {
                                type union {
                                    type enumeration {
                                        enum max                            { value -1; }
                                    }
                                    type int64;
                                }
                                description "Oper PIR.";
                            }

                            leaf exceed-droptail {
                                type union {
                                    type int64 {
                                        range "0..max";
                                    }
                                    type enumeration {
                                        enum auto                           { value -1; }
                                    }
                                }
                                description "Exceed droptail.";
                            }

                            leaf high-droptail {
                                type union {
                                    type int64 {
                                        range "0..max";
                                    }
                                    type enumeration {
                                        enum auto                           { value -1; }
                                    }
                                }
                                description "High droptail.";
                            }

                            leaf high-plus-droptail {
                                type union {
                                    type int64 {
                                        range "0..max";
                                    }
                                    type enumeration {
                                        enum auto                           { value -1; }
                                    }
                                }
                                description "Highplus droptail.";
                            }

                            leaf low-droptail {
                                type union {
                                    type int64 {
                                        range "0..max";
                                    }
                                    type enumeration {
                                        enum auto                           { value -1; }
                                    }
                                }
                                description "Low droptail.";
                            }

                            leaf operational-exceed-burst {
                                type types-qos:int64-max;
                                description "Oper burst exceed.";
                            }

                            leaf operational-max-transmit-data-size {
                                type types-qos:int64-max;
                                description "Oper max transmit data size.";
                            }

                            leaf operational-burst-fir {
                                type types-qos:int64-max;
                                description "Oper burst FIR.";
                            }

                        } // list hardware-queue

                    } // list queue

                } // list queue-group

            } // container ingress

        } // container access

    } // grouping state-port-eth-access

}
