submodule nokia-state-anysec {

    yang-version "1.1";

    belongs-to nokia-state { prefix "state"; }

    import ietf-yang-types                { prefix "yang"; }
    import nokia-sros-yang-extensions     { prefix "sros-ext"; }
    import nokia-types-security           { prefix "types-security"; }
    import nokia-types-sros               { prefix "types-sros"; }

    sros-ext:sros-major-release "rel26";
    organization "Nokia";
    contact
        "Nokia SR OS Support
         Web: <http://www.nokia.com>";
    description
        "Nokia YANG Data model with operational state for ANYsec on SR OS based routers.

         Copyright 2016 Nokia. All rights reserved. Reproduction of this document
         is authorized on the condition that the foregoing copyright notice is included.

         This nokia-state-anysec YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping state-anysec {
        container anysec {
            description "Enter the anysec context";

            leaf mka-udp-port-oper-state {
                type types-sros:oper-state;
                description "MKA UDP port operation state";
            }

            leaf srv6-sid-resolution-supported-types {
                type enumeration {
                    enum locator-type-routes            { value 1; }
                    enum all-type-routes                { value 2; }
                }
                description "SRv6 SID supported resolution types";
            }

            container mpls {
                description "Enter the mpls context";

                container security-termination-policies {
                    description "Enter the security-termination-policies context";

                    list policy {
                        key "policy-name";
                        description "Enter the policy list instance";

                        leaf policy-name {
                            type types-sros:named-item;
                            description "ANYsec security termination policy name";
                        }

                        leaf terminating-label {
                            type types-sros:mpls-label-full-range;
                            description "Terminating label";
                        }

                    } // list policy

                } // container security-termination-policies

                container tunnel-encryption {
                    description "Enter the tunnel-encryption context";

                    list encryption-group {
                        key "group-name";
                        description "Enter the encryption-group list instance";

                        leaf group-name {
                            type types-sros:named-item;
                            description "ANYsec encryption group name";
                        }

                        leaf group-id {
                            type uint32;
                            description "Encryption group ID";
                        }

                        list peer {
                            key "peer-ip-address";
                            description "Enter the peer list instance";

                            leaf peer-ip-address {
                                type types-sros:ip-unicast-address;
                                description "Peer IP address";
                            }

                            leaf tunnel-id {
                                type types-sros:tunnel-id;
                                description "Peer tunnel ID";
                            }

                            leaf encryption-label {
                                type types-sros:mpls-label-full-range;
                                description "The label uniquely identifying packets sent from this peer";
                            }

                            leaf last-inconsistent-rx-sci {
                                type binary {
                                    length "8";
                                }
                                description "The last inconsistent Rx SCI received from this peer";
                            }

                            leaf oper-state {
                                type types-sros:oper-state;
                                description "Peer operational state";
                            }

                            leaf oper-down-reason {
                                type enumeration {
                                    enum none                           { value 0; }
                                    enum peer-admin-down                { value 1; }
                                    enum encrypt-group-admin-down       { value 2; }
                                    enum term-policy-admin-down         { value 3; }
                                    enum ca-admin-down                  { value 4; }
                                    enum mka-down                       { value 5; }
                                    enum inconsistent-rx-sci            { value 6; }
                                    enum missing-rx-tunnel              { value 7; }
                                    enum missing-tx-tunnel              { value 8; }
                                }
                                description "Peer operational state down reason";
                            }

                            container rx-sc {
                                description "Enter the rx-sc context";

                                leaf rx-sci {
                                    type binary {
                                        length "8";
                                    }
                                    description "Indicates the SCI for identifying the receiving SC.";
                                }

                                leaf not-valid-packets {
                                    type yang:counter64;
                                    units "packets";
                                    description "Indicates the number of not valid packets received by this SC.";
                                }

                                leaf delayed-packets {
                                    type yang:counter64;
                                    units "packets";
                                    description
                                        "Indicates the number of received packets with the condition that the PN of the
                                         packets is lower than the lower bound of the replay protection PN.";
                                }

                                leaf unchecked-packets {
                                    type yang:counter64;
                                    units "packets";
                                    description
                                        "Indicates the number of packets that have failed the integrity check on this
                                         SC.";
                                }

                                leaf ok-packets {
                                    type yang:counter64;
                                    units "packets";
                                    description "Indicates the number of OK packets received by this SC.";
                                }

                                leaf octets-decrypted {
                                    type yang:counter64;
                                    units "octets";
                                    description
                                        "Indicates the number of octets of plain text recovered from received packets
                                         that were integrity protected and encrypted.";
                                }

                            } // container rx-sc

                            container tx-sc {
                                description "Enter the tx-sc context";

                                leaf tx-sci {
                                    type binary {
                                        length "8";
                                    }
                                    description
                                        "Indicates the Secure Channel Identifier (SCI) information for transmitting
                                         ANYsec MACsec frames. This is the same value as
                                         /state/anysec/tunnel-encryption/encryption-group/peer/mka/outbound-sci";
                                }

                                leaf encrypted-packets {
                                    type yang:counter64;
                                    units "packets";
                                    description
                                        "Indicates the number of integrity protected and encrypted packets for this
                                         transmitting SC.";
                                }

                                leaf octets-encrypted {
                                    type yang:counter64;
                                    units "octets";
                                    description
                                        "Indicates the number of plain text octets that are integrity protected and
                                         encrypted on the transmitting SC.";
                                }

                            } // container tx-sc

                            list mka {
                                key "ckn";
                                description "Enter the mka list instance";

                                leaf ckn {
                                    type binary {
                                        length "1..32";
                                    }
                                    description "Indicates CKN information for the MKA instance.";
                                }

                                leaf member-id {
                                    type binary {
                                        length "12";
                                    }
                                    description "Indicates the Member Identifier (MI) for the MKA instance.";
                                }

                                leaf outbound-sci {
                                    type binary {
                                        length "8";
                                    }
                                    description
                                        "Indicates the Secure Channel Identifier (SCI) information for transmitting
                                         ANYsec MACsec frames.";
                                }

                                leaf message-count {
                                    type uint32;
                                    description "Indicates the current count of MKA messages that is attached to MKA PDUs.";
                                }

                                leaf key-number {
                                    type uint32;
                                    description
                                        "Indicates the number of the currently assigned CAK. When a new CAK is
                                         generated, this number is incremented.";
                                }

                                leaf key-server {
                                    type boolean;
                                    description
                                        "Indicates whether this server is the highest priority server in the peer
                                         group.";
                                }

                                leaf latest-sak-an {
                                    type uint32;
                                    description
                                        "Indicates the Association Number (AN) of the latest Secure Association Key
                                         (SAK). This number is concatenated with an SCI to identify a Secure
                                         Association (SA).";
                                }

                                leaf previous-sak-an {
                                    type uint32;
                                    description
                                        "Indicates the AN of the previous SAK. This number is concatenated with an SCI
                                         to identify an SA.";
                                }

                                leaf latest-sak-ki {
                                    type binary {
                                        length "16";
                                    }
                                    description
                                        "Indicates the Key Identifier (KI) of the latest SAK. This number is derived
                                         from the MI of the key server and the key number.";
                                }

                                leaf previous-sak-ki {
                                    type binary {
                                        length "16";
                                    }
                                    description
                                        "Indicates the KI of the previous SAK. This number is derived from the MI of
                                         the key server and the key number.";
                                }

                                leaf peers-removed {
                                    type yang:counter64;
                                    description
                                        "Indicates the number of peers removed from the live/potential peer list due to
                                         not receiving an MKPDU within the MKA Live Time (6.0 sec).";
                                }

                                leaf ckn-not-found {
                                    type yang:counter64;
                                    description
                                        "Indicates the number of MKPDUs received with a CKN that does not match the CA
                                         configured for the port.";
                                }

                                leaf new-live-peer {
                                    type yang:counter64;
                                    description
                                        "Indicates the number of validated peers that have been added to the live peer
                                         list.";
                                }

                                leaf sak-generated {
                                    type yang:counter64;
                                    description "Indicates the number of SAKs generated by this MKA instance.";
                                }

                                leaf sak-installed-transmitting {
                                    type yang:counter64;
                                    description "Indicates the number of SAKs installed for transmitting.";
                                }

                                leaf sak-installed-receiving {
                                    type yang:counter64;
                                    description "Indicates the number of SAKs installed for receiving.";
                                }

                                leaf pdu-too-small {
                                    type yang:counter64;
                                    description "Indicates the number of MKPDUs received that are less than 32 octets.";
                                }

                                leaf pdu-too-big {
                                    type yang:counter64;
                                    description
                                        "Indicates the number of MKPDUs received where the EAPOL header indicates a
                                         size larger than the received packet.";
                                }

                                leaf pdu-not-quad-size {
                                    type yang:counter64;
                                    description
                                        "Indicates the number of MKPDUs received with a size that is not a multiple of
                                         4 octets.";
                                }

                                leaf pdu-invalid-number {
                                    type yang:counter64;
                                    description
                                        "Indicates the number of MKPDUs received out of order as indicated by the
                                         Message Number.";
                                }

                                leaf parameter-size-invalid {
                                    type yang:counter64;
                                    description
                                        "Indicates the number of MKPDUs received which contain a parameter set body
                                         length that exceeds the remaining length of the MKPDU.";
                                }

                                leaf liveness-check-fail {
                                    type yang:counter64;
                                    description
                                        "Indicates the number of MKPDUs received which contain an MN that is not
                                         acceptably recent.";
                                }

                                leaf parameter-not-quad-size {
                                    type yang:counter64;
                                    description
                                        "Indicates the number of MKPDUs received which contain a parameter set that is
                                         not a multiple of 4 octets.";
                                }

                                leaf unsupported-algorithm-agility {
                                    type yang:counter64;
                                    description
                                        "Indicates the number of MKPDUs received which contain an unsupported Algorithm
                                         Agility value.";
                                }

                                leaf invalid-ckn-length {
                                    type yang:counter64;
                                    description
                                        "Indicates the number of MKPDUs received which contain a CAK name that exceeds
                                         the maximum CAK name length.";
                                }

                                leaf icv-check-failed {
                                    type yang:counter64;
                                    description
                                        "Indicates the number of MKPDUs received which contain an ICV value that does
                                         not authenticate.";
                                }

                                leaf peer-same-mi {
                                    type yang:counter64;
                                    description
                                        "Indicates the number of MKPDUs received which contain a peerlist with an MI
                                         entry which conflicts with the local MI.";
                                }

                                leaf sak-non-live-peer {
                                    type yang:counter64;
                                    description
                                        "Indicates the number of SAKs received from a peer that is not a member of the
                                         Live Peers List.";
                                }

                                leaf sak-no-key-server {
                                    type yang:counter64;
                                    description
                                        "Indicates the number of SAKs received from an MKA participant that has not
                                         been designated as the Key Server.";
                                }

                                leaf sak-decrypt-fail {
                                    type yang:counter64;
                                    description
                                        "Indicates the number of AES Key Wrap SAK decryption failures that have
                                         occurred.";
                                }

                                leaf sak-encrypt-fail {
                                    type yang:counter64;
                                    description
                                        "Indicates the number of AES Key Wrap SAK encryption failures that have
                                         occurred.";
                                }

                                leaf key-number-invalid {
                                    type yang:counter64;
                                    description "Indicates the number of SAKs received with an invalid Key Number.";
                                }

                                leaf sak-install-fail {
                                    type yang:counter64;
                                    description "Indicates the number of SecY SAK installation failures that have occurred.";
                                }

                                leaf cak-info-missing {
                                    status deprecated;
                                    type yang:counter64;
                                    description
                                        "Indicates the number of times internal CAK data is not available for the
                                         generation of the SAK.";
                                }

                                leaf max-peers-set-zero {
                                    status deprecated;
                                    type yang:counter64;
                                    description
                                        "Indicates the number of SecY SAK installations that have failed due to the max
                                         peer entry being set to 0.";
                                }

                                leaf oper-state {
                                    type types-sros:oper-state;
                                    description "Indicates the operational state of the MKA participant.";
                                }

                                leaf oper-offset {
                                    type uint32 {
                                        range "0|30|50";
                                    }
                                    units "octets";
                                    description
                                        "Indicates the operational encryption offset used for the datapath PDUs when
                                         all parties in the CA have the SAK. This value is specified by the key
                                         server.";
                                }

                                leaf oper-cipher {
                                    type enumeration {
                                        enum gcm-aes-128                    { value 1; }
                                        enum gcm-aes-256                    { value 2; }
                                        enum gcm-aes-xpn-128                { value 3; }
                                        enum gcm-aes-xpn-256                { value 4; }
                                    }
                                    description
                                        "Indicates the operational encryption algorithm used for datapath PDUs when all
                                         parties in the CA have the SAK. This value is specified by the key server.";
                                }

                                leaf latest-sak-lpn {
                                    type yang:counter64;
                                    description "Indicates Lowest Acceptable Packet Number of the latest SAK.";
                                }

                                leaf previous-sak-lpn {
                                    type yang:counter64;
                                    description "Indicates Lowest Acceptable Packet Number of the previous SAK.";
                                }

                                leaf invalid-header {
                                    type yang:counter64;
                                    description "Indicates the number of MKPDUs received with an invalid MKA header.";
                                }

                                leaf cak-name {
                                    type types-security:cak-name;
                                    description "Indicates the name of the CAK in use by this MKA.";
                                }

                                leaf transmit-interval {
                                    type uint32;
                                    units "milliseconds";
                                    description
                                        "Indicates the time interval at which the MKA broadcasts its liveliness to its
                                         peers.";
                                }

                                leaf key-server-priority {
                                    type uint32;
                                    description "Indicates the priority of this MKA.";
                                }

                                leaf principal {
                                    type boolean;
                                    description "Indicates whether this MKA session is the principal session.";
                                }

                                leaf encoding-an {
                                    type union {
                                        type int32 {
                                            range "0..3";
                                        }
                                        type enumeration {
                                            enum none                           { value -1; }
                                        }
                                    }
                                    description
                                        "Indicates the Association Number (AN) of the SA currently used to encode the
                                         SecTAG for frames awaiting transmission.";
                                }

                                leaf latest-sak-receiving {
                                    type boolean;
                                    description
                                        "Indicates whether reception for the SAK is enabled for all the receive SAs
                                         identified by the AN of the latest SAK";
                                }

                                leaf latest-sak-transmitting {
                                    type boolean;
                                    description
                                        "Indicates whether the SecY is transmitting using the SAK and its own SA with the
                                         AN identified by the AN of the latest SAK.";
                                }

                                leaf previous-sak-receiving {
                                    type boolean;
                                    description
                                        "Indicates whether reception for the SAK is enabled for all the receive SAs
                                         identified by the AN of the previous SAK.";
                                }

                                leaf previous-sak-transmitting {
                                    type boolean;
                                    description
                                        "Indicates whether the SecY is transmitting using the SAK and its own SA with the
                                         AN identified bby the AN of the previous SAK.";
                                }

                                leaf psk-source {
                                    type types-security:psk-source;
                                    description "The source of the PSK.";
                                }

                                leaf unexpected-distributed-cak {
                                    type yang:counter64;
                                    description "Indicates the number of discarded distributed CAKs.";
                                }

                                leaf unexpected-distributed-sak {
                                    type yang:counter64;
                                    description "Indicates the number of discarded distributed SAKs.";
                                }

                                list mka-peer {
                                    key "member-id";
                                    description "Enter the mka-peer list instance";

                                    leaf member-id {
                                        type binary {
                                            length "12";
                                        }
                                        description "Indicates the Member Identifier (MI) for the MKA peer.";
                                    }

                                    leaf message-number {
                                        type yang:counter64;
                                        description "Indicates the latest message number of the peer entry.";
                                    }

                                    leaf type {
                                        type enumeration {
                                            enum live-peer-list                 { value 1; }
                                            enum potential-peer-list            { value 2; }
                                        }
                                        description "Indicates the type of the peer entry.";
                                    }

                                    leaf sci {
                                        type binary {
                                            length "8";
                                        }
                                        description "Indicates the SCI information of this peer list entry.";
                                    }

                                    leaf key-server-priority {
                                        type yang:counter64;
                                        description "Indicates the priority of this MKA peer.";
                                    }

                                    leaf lowest-acceptable-packet-number {
                                        type yang:counter64;
                                        description "Indicates the lowest acceptable packet number of this MKA peer.";
                                    }

                                } // list mka-peer

                            } // list mka

                        } // list peer

                    } // list encryption-group

                } // container tunnel-encryption

                container service-encryption {
                    description "Enter the service-encryption context";

                    list encryption-group {
                        key "group-name";
                        description "Enter the encryption-group list instance";

                        leaf group-name {
                            type types-sros:named-item;
                            description "ANYsec encryption group name";
                        }

                        leaf group-id {
                            type uint32;
                            description "Encryption group ID";
                        }

                        list peer {
                            key "peer-ip-address";
                            description "Enter the peer list instance";

                            leaf peer-ip-address {
                                type types-sros:ip-unicast-address;
                                description "Peer IP address";
                            }

                            leaf encryption-label {
                                type types-sros:mpls-label-full-range;
                                description "The label uniquely identifying packets sent from this peer";
                            }

                            leaf last-inconsistent-rx-sci {
                                type binary {
                                    length "8";
                                }
                                description "The last inconsistent Rx SCI received from this peer";
                            }

                            leaf oper-state {
                                type types-sros:oper-state;
                                description "Peer operational state";
                            }

                            leaf oper-down-reason {
                                type enumeration {
                                    enum none                           { value 0; }
                                    enum peer-admin-down                { value 1; }
                                    enum encrypt-group-admin-down       { value 2; }
                                    enum term-policy-admin-down         { value 3; }
                                    enum ca-admin-down                  { value 4; }
                                    enum mka-down                       { value 5; }
                                    enum inconsistent-rx-sci            { value 6; }
                                    enum missing-rx-tunnel              { value 7; }
                                    enum missing-tx-tunnel              { value 8; }
                                }
                                description "Peer operational state down reason";
                            }

                            container rx-sc {
                                description "Enter the rx-sc context";

                                leaf rx-sci {
                                    type binary {
                                        length "8";
                                    }
                                    description "Indicates the SCI for identifying the receiving SC.";
                                }

                                leaf not-valid-packets {
                                    type yang:counter64;
                                    units "packets";
                                    description "Indicates the number of not valid packets received by this SC.";
                                }

                                leaf delayed-packets {
                                    type yang:counter64;
                                    units "packets";
                                    description
                                        "Indicates the number of received packets with the condition that the PN of the
                                         packets is lower than the lower bound of the replay protection PN.";
                                }

                                leaf unchecked-packets {
                                    type yang:counter64;
                                    units "packets";
                                    description
                                        "Indicates the number of packets that have failed the integrity check on this
                                         SC.";
                                }

                                leaf ok-packets {
                                    type yang:counter64;
                                    units "packets";
                                    description "Indicates the number of OK packets received by this SC.";
                                }

                                leaf octets-decrypted {
                                    type yang:counter64;
                                    units "octets";
                                    description
                                        "Indicates the number of octets of plain text recovered from received packets
                                         that were integrity protected and encrypted.";
                                }

                            } // container rx-sc

                            container tx-sc {
                                description "Enter the tx-sc context";

                                leaf tx-sci {
                                    type binary {
                                        length "8";
                                    }
                                    description
                                        "Indicates the Secure Channel Identifier (SCI) information for transmitting
                                         ANYsec MACsec frames. This is the same value as
                                         /state/anysec/tunnel-encryption/encryption-group/peer/mka/outbound-sci";
                                }

                                leaf encrypted-packets {
                                    type yang:counter64;
                                    units "packets";
                                    description
                                        "Indicates the number of integrity protected and encrypted packets for this
                                         transmitting SC.";
                                }

                                leaf octets-encrypted {
                                    type yang:counter64;
                                    units "octets";
                                    description
                                        "Indicates the number of plain text octets that are integrity protected and
                                         encrypted on the transmitting SC.";
                                }

                            } // container tx-sc

                            list mka {
                                key "ckn";
                                description "Enter the mka list instance";

                                leaf ckn {
                                    type binary {
                                        length "1..32";
                                    }
                                    description "Indicates CKN information for the MKA instance.";
                                }

                                leaf member-id {
                                    type binary {
                                        length "12";
                                    }
                                    description "Indicates the Member Identifier (MI) for the MKA instance.";
                                }

                                leaf outbound-sci {
                                    type binary {
                                        length "8";
                                    }
                                    description
                                        "Indicates the Secure Channel Identifier (SCI) information for transmitting
                                         ANYsec MACsec frames.";
                                }

                                leaf message-count {
                                    type uint32;
                                    description "Indicates the current count of MKA messages that is attached to MKA PDUs.";
                                }

                                leaf key-number {
                                    type uint32;
                                    description
                                        "Indicates the number of the currently assigned CAK. When a new CAK is
                                         generated, this number is incremented.";
                                }

                                leaf key-server {
                                    type boolean;
                                    description
                                        "Indicates whether this server is the highest priority server in the peer
                                         group.";
                                }

                                leaf latest-sak-an {
                                    type uint32;
                                    description
                                        "Indicates the Association Number (AN) of the latest Secure Association Key
                                         (SAK). This number is concatenated with an SCI to identify a Secure
                                         Association (SA).";
                                }

                                leaf previous-sak-an {
                                    type uint32;
                                    description
                                        "Indicates the AN of the previous SAK. This number is concatenated with an SCI
                                         to identify an SA.";
                                }

                                leaf latest-sak-ki {
                                    type binary {
                                        length "16";
                                    }
                                    description
                                        "Indicates the Key Identifier (KI) of the latest SAK. This number is derived
                                         from the MI of the key server and the key number.";
                                }

                                leaf previous-sak-ki {
                                    type binary {
                                        length "16";
                                    }
                                    description
                                        "Indicates the KI of the previous SAK. This number is derived from the MI of
                                         the key server and the key number.";
                                }

                                leaf peers-removed {
                                    type yang:counter64;
                                    description
                                        "Indicates the number of peers removed from the live/potential peer list due to
                                         not receiving an MKPDU within the MKA Live Time (6.0 sec).";
                                }

                                leaf ckn-not-found {
                                    type yang:counter64;
                                    description
                                        "Indicates the number of MKPDUs received with a CKN that does not match the CA
                                         configured for the port.";
                                }

                                leaf new-live-peer {
                                    type yang:counter64;
                                    description
                                        "Indicates the number of validated peers that have been added to the live peer
                                         list.";
                                }

                                leaf sak-generated {
                                    type yang:counter64;
                                    description "Indicates the number of SAKs generated by this MKA instance.";
                                }

                                leaf sak-installed-transmitting {
                                    type yang:counter64;
                                    description "Indicates the number of SAKs installed for transmitting.";
                                }

                                leaf sak-installed-receiving {
                                    type yang:counter64;
                                    description "Indicates the number of SAKs installed for receiving.";
                                }

                                leaf pdu-too-small {
                                    type yang:counter64;
                                    description "Indicates the number of MKPDUs received that are less than 32 octets.";
                                }

                                leaf pdu-too-big {
                                    type yang:counter64;
                                    description
                                        "Indicates the number of MKPDUs received where the EAPOL header indicates a
                                         size larger than the received packet.";
                                }

                                leaf pdu-not-quad-size {
                                    type yang:counter64;
                                    description
                                        "Indicates the number of MKPDUs received with a size that is not a multiple of
                                         4 octets.";
                                }

                                leaf pdu-invalid-number {
                                    type yang:counter64;
                                    description
                                        "Indicates the number of MKPDUs received out of order as indicated by the
                                         Message Number.";
                                }

                                leaf parameter-size-invalid {
                                    type yang:counter64;
                                    description
                                        "Indicates the number of MKPDUs received which contain a parameter set body
                                         length that exceeds the remaining length of the MKPDU.";
                                }

                                leaf liveness-check-fail {
                                    type yang:counter64;
                                    description
                                        "Indicates the number of MKPDUs received which contain an MN that is not
                                         acceptably recent.";
                                }

                                leaf parameter-not-quad-size {
                                    type yang:counter64;
                                    description
                                        "Indicates the number of MKPDUs received which contain a parameter set that is
                                         not a multiple of 4 octets.";
                                }

                                leaf unsupported-algorithm-agility {
                                    type yang:counter64;
                                    description
                                        "Indicates the number of MKPDUs received which contain an unsupported Algorithm
                                         Agility value.";
                                }

                                leaf invalid-ckn-length {
                                    type yang:counter64;
                                    description
                                        "Indicates the number of MKPDUs received which contain a CAK name that exceeds
                                         the maximum CAK name length.";
                                }

                                leaf icv-check-failed {
                                    type yang:counter64;
                                    description
                                        "Indicates the number of MKPDUs received which contain an ICV value that does
                                         not authenticate.";
                                }

                                leaf peer-same-mi {
                                    type yang:counter64;
                                    description
                                        "Indicates the number of MKPDUs received which contain a peerlist with an MI
                                         entry which conflicts with the local MI.";
                                }

                                leaf sak-non-live-peer {
                                    type yang:counter64;
                                    description
                                        "Indicates the number of SAKs received from a peer that is not a member of the
                                         Live Peers List.";
                                }

                                leaf sak-no-key-server {
                                    type yang:counter64;
                                    description
                                        "Indicates the number of SAKs received from an MKA participant that has not
                                         been designated as the Key Server.";
                                }

                                leaf sak-decrypt-fail {
                                    type yang:counter64;
                                    description
                                        "Indicates the number of AES Key Wrap SAK decryption failures that have
                                         occurred.";
                                }

                                leaf sak-encrypt-fail {
                                    type yang:counter64;
                                    description
                                        "Indicates the number of AES Key Wrap SAK encryption failures that have
                                         occurred.";
                                }

                                leaf key-number-invalid {
                                    type yang:counter64;
                                    description "Indicates the number of SAKs received with an invalid Key Number.";
                                }

                                leaf sak-install-fail {
                                    type yang:counter64;
                                    description "Indicates the number of SecY SAK installation failures that have occurred.";
                                }

                                leaf cak-info-missing {
                                    status deprecated;
                                    type yang:counter64;
                                    description
                                        "Indicates the number of times internal CAK data is not available for the
                                         generation of the SAK.";
                                }

                                leaf max-peers-set-zero {
                                    status deprecated;
                                    type yang:counter64;
                                    description
                                        "Indicates the number of SecY SAK installations that have failed due to the max
                                         peer entry being set to 0.";
                                }

                                leaf oper-state {
                                    type types-sros:oper-state;
                                    description "Indicates the operational state of the MKA participant.";
                                }

                                leaf oper-offset {
                                    type uint32 {
                                        range "0|30|50";
                                    }
                                    units "octets";
                                    description
                                        "Indicates the operational encryption offset used for the datapath PDUs when
                                         all parties in the CA have the SAK. This value is specified by the key
                                         server.";
                                }

                                leaf oper-cipher {
                                    type enumeration {
                                        enum gcm-aes-128                    { value 1; }
                                        enum gcm-aes-256                    { value 2; }
                                        enum gcm-aes-xpn-128                { value 3; }
                                        enum gcm-aes-xpn-256                { value 4; }
                                    }
                                    description
                                        "Indicates the operational encryption algorithm used for datapath PDUs when all
                                         parties in the CA have the SAK. This value is specified by the key server.";
                                }

                                leaf latest-sak-lpn {
                                    type yang:counter64;
                                    description "Indicates Lowest Acceptable Packet Number of the latest SAK.";
                                }

                                leaf previous-sak-lpn {
                                    type yang:counter64;
                                    description "Indicates Lowest Acceptable Packet Number of the previous SAK.";
                                }

                                leaf invalid-header {
                                    type yang:counter64;
                                    description "Indicates the number of MKPDUs received with an invalid MKA header.";
                                }

                                leaf cak-name {
                                    type types-security:cak-name;
                                    description "Indicates the name of the CAK in use by this MKA.";
                                }

                                leaf transmit-interval {
                                    type uint32;
                                    units "milliseconds";
                                    description
                                        "Indicates the time interval at which the MKA broadcasts its liveliness to its
                                         peers.";
                                }

                                leaf key-server-priority {
                                    type uint32;
                                    description "Indicates the priority of this MKA.";
                                }

                                leaf principal {
                                    type boolean;
                                    description "Indicates whether this MKA session is the principal session.";
                                }

                                leaf encoding-an {
                                    type union {
                                        type int32 {
                                            range "0..3";
                                        }
                                        type enumeration {
                                            enum none                           { value -1; }
                                        }
                                    }
                                    description
                                        "Indicates the Association Number (AN) of the SA currently used to encode the
                                         SecTAG for frames awaiting transmission.";
                                }

                                leaf latest-sak-receiving {
                                    type boolean;
                                    description
                                        "Indicates whether reception for the SAK is enabled for all the receive SAs
                                         identified by the AN of the latest SAK";
                                }

                                leaf latest-sak-transmitting {
                                    type boolean;
                                    description
                                        "Indicates whether the SecY is transmitting using the SAK and its own SA with the
                                         AN identified by the AN of the latest SAK.";
                                }

                                leaf previous-sak-receiving {
                                    type boolean;
                                    description
                                        "Indicates whether reception for the SAK is enabled for all the receive SAs
                                         identified by the AN of the previous SAK.";
                                }

                                leaf previous-sak-transmitting {
                                    type boolean;
                                    description
                                        "Indicates whether the SecY is transmitting using the SAK and its own SA with the
                                         AN identified bby the AN of the previous SAK.";
                                }

                                leaf psk-source {
                                    type types-security:psk-source;
                                    description "The source of the PSK.";
                                }

                                leaf unexpected-distributed-cak {
                                    type yang:counter64;
                                    description "Indicates the number of discarded distributed CAKs.";
                                }

                                leaf unexpected-distributed-sak {
                                    type yang:counter64;
                                    description "Indicates the number of discarded distributed SAKs.";
                                }

                                list mka-peer {
                                    key "member-id";
                                    description "Enter the mka-peer list instance";

                                    leaf member-id {
                                        type binary {
                                            length "12";
                                        }
                                        description "Indicates the Member Identifier (MI) for the MKA peer.";
                                    }

                                    leaf message-number {
                                        type yang:counter64;
                                        description "Indicates the latest message number of the peer entry.";
                                    }

                                    leaf type {
                                        type enumeration {
                                            enum live-peer-list                 { value 1; }
                                            enum potential-peer-list            { value 2; }
                                        }
                                        description "Indicates the type of the peer entry.";
                                    }

                                    leaf sci {
                                        type binary {
                                            length "8";
                                        }
                                        description "Indicates the SCI information of this peer list entry.";
                                    }

                                    leaf key-server-priority {
                                        type yang:counter64;
                                        description "Indicates the priority of this MKA peer.";
                                    }

                                    leaf lowest-acceptable-packet-number {
                                        type yang:counter64;
                                        description "Indicates the lowest acceptable packet number of this MKA peer.";
                                    }

                                } // list mka-peer

                            } // list mka

                        } // list peer

                    } // list encryption-group

                } // container service-encryption

            } // container mpls

            container segment-routing-v6 {
                description "Enter the segment-routing-v6 context";

                container service-encryption {
                    description "Enter the service-encryption context";

                    list encryption-group {
                        key "group-name";
                        description "Enter the encryption-group list instance";

                        leaf group-name {
                            type types-sros:named-item;
                            description "ANYsec encryption group name";
                        }

                        leaf group-id {
                            type uint32;
                            description "Encryption group ID";
                        }

                        list peer {
                            key "peer-ip-address";
                            description "Enter the peer list instance";

                            leaf peer-ip-address {
                                type types-sros:ip-unicast-address;
                                description "Peer IP address";
                            }

                            leaf encryption-label {
                                type types-sros:mpls-label-full-range;
                                description "The label uniquely identifying packets sent from this peer";
                            }

                            leaf last-inconsistent-rx-sci {
                                type binary {
                                    length "8";
                                }
                                description "The last inconsistent Rx SCI received from this peer";
                            }

                            leaf oper-state {
                                type types-sros:oper-state;
                                description "Peer operational state";
                            }

                            leaf oper-down-reason {
                                type enumeration {
                                    enum none                           { value 0; }
                                    enum peer-admin-down                { value 1; }
                                    enum encrypt-group-admin-down       { value 2; }
                                    enum term-policy-admin-down         { value 3; }
                                    enum ca-admin-down                  { value 4; }
                                    enum mka-down                       { value 5; }
                                    enum inconsistent-rx-sci            { value 6; }
                                    enum missing-rx-tunnel              { value 7; }
                                    enum missing-tx-tunnel              { value 8; }
                                }
                                description "Peer operational state down reason";
                            }

                            container rx-sc {
                                description "Enter the rx-sc context";

                                leaf rx-sci {
                                    type binary {
                                        length "8";
                                    }
                                    description "Indicates the SCI for identifying the receiving SC.";
                                }

                                leaf not-valid-packets {
                                    type yang:counter64;
                                    units "packets";
                                    description "Indicates the number of not valid packets received by this SC.";
                                }

                                leaf delayed-packets {
                                    type yang:counter64;
                                    units "packets";
                                    description
                                        "Indicates the number of received packets with the condition that the PN of the
                                         packets is lower than the lower bound of the replay protection PN.";
                                }

                                leaf unchecked-packets {
                                    type yang:counter64;
                                    units "packets";
                                    description
                                        "Indicates the number of packets that have failed the integrity check on this
                                         SC.";
                                }

                                leaf ok-packets {
                                    type yang:counter64;
                                    units "packets";
                                    description "Indicates the number of OK packets received by this SC.";
                                }

                                leaf octets-decrypted {
                                    type yang:counter64;
                                    units "octets";
                                    description
                                        "Indicates the number of octets of plain text recovered from received packets
                                         that were integrity protected and encrypted.";
                                }

                            } // container rx-sc

                            container tx-sc {
                                description "Enter the tx-sc context";

                                leaf tx-sci {
                                    type binary {
                                        length "8";
                                    }
                                    description
                                        "Indicates the Secure Channel Identifier (SCI) information for transmitting
                                         ANYsec MACsec frames. This is the same value as
                                         /state/anysec/tunnel-encryption/encryption-group/peer/mka/outbound-sci";
                                }

                                leaf encrypted-packets {
                                    type yang:counter64;
                                    units "packets";
                                    description
                                        "Indicates the number of integrity protected and encrypted packets for this
                                         transmitting SC.";
                                }

                                leaf octets-encrypted {
                                    type yang:counter64;
                                    units "octets";
                                    description
                                        "Indicates the number of plain text octets that are integrity protected and
                                         encrypted on the transmitting SC.";
                                }

                            } // container tx-sc

                            list mka {
                                key "ckn";
                                description "Enter the mka list instance";

                                leaf ckn {
                                    type binary {
                                        length "1..32";
                                    }
                                    description "Indicates CKN information for the MKA instance.";
                                }

                                leaf member-id {
                                    type binary {
                                        length "12";
                                    }
                                    description "Indicates the Member Identifier (MI) for the MKA instance.";
                                }

                                leaf outbound-sci {
                                    type binary {
                                        length "8";
                                    }
                                    description
                                        "Indicates the Secure Channel Identifier (SCI) information for transmitting
                                         ANYsec MACsec frames.";
                                }

                                leaf message-count {
                                    type uint32;
                                    description "Indicates the current count of MKA messages that is attached to MKA PDUs.";
                                }

                                leaf key-number {
                                    type uint32;
                                    description
                                        "Indicates the number of the currently assigned CAK. When a new CAK is
                                         generated, this number is incremented.";
                                }

                                leaf key-server {
                                    type boolean;
                                    description
                                        "Indicates whether this server is the highest priority server in the peer
                                         group.";
                                }

                                leaf latest-sak-an {
                                    type uint32;
                                    description
                                        "Indicates the Association Number (AN) of the latest Secure Association Key
                                         (SAK). This number is concatenated with an SCI to identify a Secure
                                         Association (SA).";
                                }

                                leaf previous-sak-an {
                                    type uint32;
                                    description
                                        "Indicates the AN of the previous SAK. This number is concatenated with an SCI
                                         to identify an SA.";
                                }

                                leaf latest-sak-ki {
                                    type binary {
                                        length "16";
                                    }
                                    description
                                        "Indicates the Key Identifier (KI) of the latest SAK. This number is derived
                                         from the MI of the key server and the key number.";
                                }

                                leaf previous-sak-ki {
                                    type binary {
                                        length "16";
                                    }
                                    description
                                        "Indicates the KI of the previous SAK. This number is derived from the MI of
                                         the key server and the key number.";
                                }

                                leaf peers-removed {
                                    type yang:counter64;
                                    description
                                        "Indicates the number of peers removed from the live/potential peer list due to
                                         not receiving an MKPDU within the MKA Live Time (6.0 sec).";
                                }

                                leaf ckn-not-found {
                                    type yang:counter64;
                                    description
                                        "Indicates the number of MKPDUs received with a CKN that does not match the CA
                                         configured for the port.";
                                }

                                leaf new-live-peer {
                                    type yang:counter64;
                                    description
                                        "Indicates the number of validated peers that have been added to the live peer
                                         list.";
                                }

                                leaf sak-generated {
                                    type yang:counter64;
                                    description "Indicates the number of SAKs generated by this MKA instance.";
                                }

                                leaf sak-installed-transmitting {
                                    type yang:counter64;
                                    description "Indicates the number of SAKs installed for transmitting.";
                                }

                                leaf sak-installed-receiving {
                                    type yang:counter64;
                                    description "Indicates the number of SAKs installed for receiving.";
                                }

                                leaf pdu-too-small {
                                    type yang:counter64;
                                    description "Indicates the number of MKPDUs received that are less than 32 octets.";
                                }

                                leaf pdu-too-big {
                                    type yang:counter64;
                                    description
                                        "Indicates the number of MKPDUs received where the EAPOL header indicates a
                                         size larger than the received packet.";
                                }

                                leaf pdu-not-quad-size {
                                    type yang:counter64;
                                    description
                                        "Indicates the number of MKPDUs received with a size that is not a multiple of
                                         4 octets.";
                                }

                                leaf pdu-invalid-number {
                                    type yang:counter64;
                                    description
                                        "Indicates the number of MKPDUs received out of order as indicated by the
                                         Message Number.";
                                }

                                leaf parameter-size-invalid {
                                    type yang:counter64;
                                    description
                                        "Indicates the number of MKPDUs received which contain a parameter set body
                                         length that exceeds the remaining length of the MKPDU.";
                                }

                                leaf liveness-check-fail {
                                    type yang:counter64;
                                    description
                                        "Indicates the number of MKPDUs received which contain an MN that is not
                                         acceptably recent.";
                                }

                                leaf parameter-not-quad-size {
                                    type yang:counter64;
                                    description
                                        "Indicates the number of MKPDUs received which contain a parameter set that is
                                         not a multiple of 4 octets.";
                                }

                                leaf unsupported-algorithm-agility {
                                    type yang:counter64;
                                    description
                                        "Indicates the number of MKPDUs received which contain an unsupported Algorithm
                                         Agility value.";
                                }

                                leaf invalid-ckn-length {
                                    type yang:counter64;
                                    description
                                        "Indicates the number of MKPDUs received which contain a CAK name that exceeds
                                         the maximum CAK name length.";
                                }

                                leaf icv-check-failed {
                                    type yang:counter64;
                                    description
                                        "Indicates the number of MKPDUs received which contain an ICV value that does
                                         not authenticate.";
                                }

                                leaf peer-same-mi {
                                    type yang:counter64;
                                    description
                                        "Indicates the number of MKPDUs received which contain a peerlist with an MI
                                         entry which conflicts with the local MI.";
                                }

                                leaf sak-non-live-peer {
                                    type yang:counter64;
                                    description
                                        "Indicates the number of SAKs received from a peer that is not a member of the
                                         Live Peers List.";
                                }

                                leaf sak-no-key-server {
                                    type yang:counter64;
                                    description
                                        "Indicates the number of SAKs received from an MKA participant that has not
                                         been designated as the Key Server.";
                                }

                                leaf sak-decrypt-fail {
                                    type yang:counter64;
                                    description
                                        "Indicates the number of AES Key Wrap SAK decryption failures that have
                                         occurred.";
                                }

                                leaf sak-encrypt-fail {
                                    type yang:counter64;
                                    description
                                        "Indicates the number of AES Key Wrap SAK encryption failures that have
                                         occurred.";
                                }

                                leaf key-number-invalid {
                                    type yang:counter64;
                                    description "Indicates the number of SAKs received with an invalid Key Number.";
                                }

                                leaf sak-install-fail {
                                    type yang:counter64;
                                    description "Indicates the number of SecY SAK installation failures that have occurred.";
                                }

                                leaf cak-info-missing {
                                    status deprecated;
                                    type yang:counter64;
                                    description
                                        "Indicates the number of times internal CAK data is not available for the
                                         generation of the SAK.";
                                }

                                leaf max-peers-set-zero {
                                    status deprecated;
                                    type yang:counter64;
                                    description
                                        "Indicates the number of SecY SAK installations that have failed due to the max
                                         peer entry being set to 0.";
                                }

                                leaf oper-state {
                                    type types-sros:oper-state;
                                    description "Indicates the operational state of the MKA participant.";
                                }

                                leaf oper-offset {
                                    type uint32 {
                                        range "0|30|50";
                                    }
                                    units "octets";
                                    description
                                        "Indicates the operational encryption offset used for the datapath PDUs when
                                         all parties in the CA have the SAK. This value is specified by the key
                                         server.";
                                }

                                leaf oper-cipher {
                                    type enumeration {
                                        enum gcm-aes-128                    { value 1; }
                                        enum gcm-aes-256                    { value 2; }
                                        enum gcm-aes-xpn-128                { value 3; }
                                        enum gcm-aes-xpn-256                { value 4; }
                                    }
                                    description
                                        "Indicates the operational encryption algorithm used for datapath PDUs when all
                                         parties in the CA have the SAK. This value is specified by the key server.";
                                }

                                leaf latest-sak-lpn {
                                    type yang:counter64;
                                    description "Indicates Lowest Acceptable Packet Number of the latest SAK.";
                                }

                                leaf previous-sak-lpn {
                                    type yang:counter64;
                                    description "Indicates Lowest Acceptable Packet Number of the previous SAK.";
                                }

                                leaf invalid-header {
                                    type yang:counter64;
                                    description "Indicates the number of MKPDUs received with an invalid MKA header.";
                                }

                                leaf cak-name {
                                    type types-security:cak-name;
                                    description "Indicates the name of the CAK in use by this MKA.";
                                }

                                leaf transmit-interval {
                                    type uint32;
                                    units "milliseconds";
                                    description
                                        "Indicates the time interval at which the MKA broadcasts its liveliness to its
                                         peers.";
                                }

                                leaf key-server-priority {
                                    type uint32;
                                    description "Indicates the priority of this MKA.";
                                }

                                leaf principal {
                                    type boolean;
                                    description "Indicates whether this MKA session is the principal session.";
                                }

                                leaf encoding-an {
                                    type union {
                                        type int32 {
                                            range "0..3";
                                        }
                                        type enumeration {
                                            enum none                           { value -1; }
                                        }
                                    }
                                    description
                                        "Indicates the Association Number (AN) of the SA currently used to encode the
                                         SecTAG for frames awaiting transmission.";
                                }

                                leaf latest-sak-receiving {
                                    type boolean;
                                    description
                                        "Indicates whether reception for the SAK is enabled for all the receive SAs
                                         identified by the AN of the latest SAK";
                                }

                                leaf latest-sak-transmitting {
                                    type boolean;
                                    description
                                        "Indicates whether the SecY is transmitting using the SAK and its own SA with the
                                         AN identified by the AN of the latest SAK.";
                                }

                                leaf previous-sak-receiving {
                                    type boolean;
                                    description
                                        "Indicates whether reception for the SAK is enabled for all the receive SAs
                                         identified by the AN of the previous SAK.";
                                }

                                leaf previous-sak-transmitting {
                                    type boolean;
                                    description
                                        "Indicates whether the SecY is transmitting using the SAK and its own SA with the
                                         AN identified bby the AN of the previous SAK.";
                                }

                                leaf psk-source {
                                    type types-security:psk-source;
                                    description "The source of the PSK.";
                                }

                                leaf unexpected-distributed-cak {
                                    type yang:counter64;
                                    description "Indicates the number of discarded distributed CAKs.";
                                }

                                leaf unexpected-distributed-sak {
                                    type yang:counter64;
                                    description "Indicates the number of discarded distributed SAKs.";
                                }

                                list mka-peer {
                                    key "member-id";
                                    description "Enter the mka-peer list instance";

                                    leaf member-id {
                                        type binary {
                                            length "12";
                                        }
                                        description "Indicates the Member Identifier (MI) for the MKA peer.";
                                    }

                                    leaf message-number {
                                        type yang:counter64;
                                        description "Indicates the latest message number of the peer entry.";
                                    }

                                    leaf type {
                                        type enumeration {
                                            enum live-peer-list                 { value 1; }
                                            enum potential-peer-list            { value 2; }
                                        }
                                        description "Indicates the type of the peer entry.";
                                    }

                                    leaf sci {
                                        type binary {
                                            length "8";
                                        }
                                        description "Indicates the SCI information of this peer list entry.";
                                    }

                                    leaf key-server-priority {
                                        type yang:counter64;
                                        description "Indicates the priority of this MKA peer.";
                                    }

                                    leaf lowest-acceptable-packet-number {
                                        type yang:counter64;
                                        description "Indicates the lowest acceptable packet number of this MKA peer.";
                                    }

                                } // list mka-peer

                            } // list mka

                        } // list peer

                    } // list encryption-group

                } // container service-encryption

            } // container segment-routing-v6

            container security-termination-policies {
                status obsolete;
                description "Enter the security-termination-policies context";

                list policy {
                    status obsolete;
                    key "policy-name";
                    description "Enter the policy list instance";

                    leaf policy-name {
                        status obsolete;
                        type types-sros:named-item;
                        description "ANYsec security termination policy name";
                    }

                    leaf terminating-label {
                        status obsolete;
                        type types-sros:mpls-label-full-range;
                        description "Terminating label";
                    }

                } // list policy

            } // container security-termination-policies

            container tunnel-encryption {
                status obsolete;
                description "Enter the tunnel-encryption context";

                list security-termination-policy {
                    status obsolete;
                    key "policy-name";
                    description "Enter the security-termination-policy list instance";

                    leaf policy-name {
                        status obsolete;
                        type types-sros:named-item;
                        description "ANYsec security termination policy name";
                    }

                    leaf terminating-label {
                        status obsolete;
                        type types-sros:mpls-label-full-range;
                        description "Terminating label";
                    }

                } // list security-termination-policy

                list encryption-group {
                    status obsolete;
                    key "group-name";
                    description "Enter the encryption-group list instance";

                    leaf group-name {
                        status obsolete;
                        type types-sros:named-item;
                        description "ANYsec encryption group name";
                    }

                    leaf group-id {
                        status obsolete;
                        type uint32;
                        description "Encryption group ID";
                    }

                    list peer {
                        status obsolete;
                        key "peer-ip-address";
                        description "Enter the peer list instance";

                        leaf peer-ip-address {
                            status obsolete;
                            type types-sros:ip-unicast-address;
                            description "Peer IP address";
                        }

                        leaf tunnel-id {
                            status obsolete;
                            type types-sros:tunnel-id;
                            description "Peer tunnel ID";
                        }

                        leaf encryption-label {
                            status obsolete;
                            type types-sros:mpls-label-full-range;
                            description "The label uniquely identifying packets sent from this peer";
                        }

                        leaf last-inconsistent-rx-sci {
                            status obsolete;
                            type binary {
                                length "8";
                            }
                            description "The last inconsistent Rx SCI received from this peer";
                        }

                        leaf oper-state {
                            status obsolete;
                            type types-sros:oper-state;
                            description "Peer operational state";
                        }

                        leaf oper-down-reason {
                            status obsolete;
                            type enumeration {
                                enum none                           { value 0; }
                                enum peer-admin-down                { value 1; }
                                enum encrypt-group-admin-down       { value 2; }
                                enum term-policy-admin-down         { value 3; }
                                enum ca-admin-down                  { value 4; }
                                enum mka-down                       { value 5; }
                                enum inconsistent-rx-sci            { value 6; }
                                enum missing-rx-tunnel              { value 7; }
                                enum missing-tx-tunnel              { value 8; }
                            }
                            description "Peer operational state down reason";
                        }

                        container rx-sc {
                            status obsolete;
                            description "Enter the rx-sc context";

                            leaf rx-sci {
                                status obsolete;
                                type binary {
                                    length "8";
                                }
                                description "Indicates the SCI for identifying the receiving SC.";
                            }

                            leaf not-valid-packets {
                                status obsolete;
                                type yang:counter64;
                                units "packets";
                                description "Indicates the number of not valid packets received by this SC.";
                            }

                            leaf delayed-packets {
                                status obsolete;
                                type yang:counter64;
                                units "packets";
                                description
                                    "Indicates the number of received packets with the condition that the PN of the
                                     packets is lower than the lower bound of the replay protection PN.";
                            }

                            leaf unchecked-packets {
                                status obsolete;
                                type yang:counter64;
                                units "packets";
                                description
                                    "Indicates the number of packets that have failed the integrity check on this
                                     SC.";
                            }

                            leaf ok-packets {
                                status obsolete;
                                type yang:counter64;
                                units "packets";
                                description "Indicates the number of OK packets received by this SC.";
                            }

                            leaf octets-decrypted {
                                status obsolete;
                                type yang:counter64;
                                units "octets";
                                description
                                    "Indicates the number of octets of plain text recovered from received packets
                                     that were integrity protected and encrypted.";
                            }

                        } // container rx-sc

                        container tx-sc {
                            status obsolete;
                            description "Enter the tx-sc context";

                            leaf tx-sci {
                                status obsolete;
                                type binary {
                                    length "8";
                                }
                                description
                                    "Indicates the Secure Channel Identifier (SCI) information for transmitting
                                     ANYsec MACsec frames. This is the same value as
                                     /state/anysec/tunnel-encryption/encryption-group/peer/mka/outbound-sci";
                            }

                            leaf encrypted-packets {
                                status obsolete;
                                type yang:counter64;
                                units "packets";
                                description
                                    "Indicates the number of integrity protected and encrypted packets for this
                                     transmitting SC.";
                            }

                            leaf octets-encrypted {
                                status obsolete;
                                type yang:counter64;
                                units "octets";
                                description
                                    "Indicates the number of plain text octets that are integrity protected and
                                     encrypted on the transmitting SC.";
                            }

                        } // container tx-sc

                        list mka {
                            status obsolete;
                            key "ckn";
                            description "Enter the mka list instance";

                            leaf ckn {
                                status obsolete;
                                type binary {
                                    length "1..32";
                                }
                                description "Indicates CKN information for the MKA instance.";
                            }

                            leaf member-id {
                                status obsolete;
                                type binary {
                                    length "12";
                                }
                                description "Indicates the Member Identifier (MI) for the MKA instance.";
                            }

                            leaf outbound-sci {
                                status obsolete;
                                type binary {
                                    length "8";
                                }
                                description
                                    "Indicates the Secure Channel Identifier (SCI) information for transmitting
                                     ANYsec MACsec frames.";
                            }

                            leaf message-count {
                                status obsolete;
                                type uint32;
                                description "Indicates the current count of MKA messages that is attached to MKA PDUs.";
                            }

                            leaf key-number {
                                status obsolete;
                                type uint32;
                                description
                                    "Indicates the number of the currently assigned CAK. When a new CAK is
                                     generated, this number is incremented.";
                            }

                            leaf key-server {
                                status obsolete;
                                type boolean;
                                description
                                    "Indicates whether this server is the highest priority server in the peer
                                     group.";
                            }

                            leaf latest-sak-an {
                                status obsolete;
                                type uint32;
                                description
                                    "Indicates the Association Number (AN) of the latest Secure Association Key
                                     (SAK). This number is concatenated with an SCI to identify a Secure
                                     Association (SA).";
                            }

                            leaf previous-sak-an {
                                status obsolete;
                                type uint32;
                                description
                                    "Indicates the AN of the previous SAK. This number is concatenated with an SCI
                                     to identify an SA.";
                            }

                            leaf latest-sak-ki {
                                status obsolete;
                                type binary {
                                    length "16";
                                }
                                description
                                    "Indicates the Key Identifier (KI) of the latest SAK. This number is derived
                                     from the MI of the key server and the key number.";
                            }

                            leaf previous-sak-ki {
                                status obsolete;
                                type binary {
                                    length "16";
                                }
                                description
                                    "Indicates the KI of the previous SAK. This number is derived from the MI of
                                     the key server and the key number.";
                            }

                            leaf peers-removed {
                                status obsolete;
                                type yang:counter64;
                                description
                                    "Indicates the number of peers removed from the live/potential peer list due to
                                     not receiving an MKPDU within the MKA Live Time (6.0 sec).";
                            }

                            leaf ckn-not-found {
                                status obsolete;
                                type yang:counter64;
                                description
                                    "Indicates the number of MKPDUs received with a CKN that does not match the CA
                                     configured for the port.";
                            }

                            leaf new-live-peer {
                                status obsolete;
                                type yang:counter64;
                                description
                                    "Indicates the number of validated peers that have been added to the live peer
                                     list.";
                            }

                            leaf sak-generated {
                                status obsolete;
                                type yang:counter64;
                                description "Indicates the number of SAKs generated by this MKA instance.";
                            }

                            leaf sak-installed-transmitting {
                                status obsolete;
                                type yang:counter64;
                                description "Indicates the number of SAKs installed for transmitting.";
                            }

                            leaf sak-installed-receiving {
                                status obsolete;
                                type yang:counter64;
                                description "Indicates the number of SAKs installed for receiving.";
                            }

                            leaf pdu-too-small {
                                status obsolete;
                                type yang:counter64;
                                description "Indicates the number of MKPDUs received that are less than 32 octets.";
                            }

                            leaf pdu-too-big {
                                status obsolete;
                                type yang:counter64;
                                description
                                    "Indicates the number of MKPDUs received where the EAPOL header indicates a
                                     size larger than the received packet.";
                            }

                            leaf pdu-not-quad-size {
                                status obsolete;
                                type yang:counter64;
                                description
                                    "Indicates the number of MKPDUs received with a size that is not a multiple of
                                     4 octets.";
                            }

                            leaf pdu-invalid-number {
                                status obsolete;
                                type yang:counter64;
                                description
                                    "Indicates the number of MKPDUs received out of order as indicated by the
                                     Message Number.";
                            }

                            leaf parameter-size-invalid {
                                status obsolete;
                                type yang:counter64;
                                description
                                    "Indicates the number of MKPDUs received which contain a parameter set body
                                     length that exceeds the remaining length of the MKPDU.";
                            }

                            leaf liveness-check-fail {
                                status obsolete;
                                type yang:counter64;
                                description
                                    "Indicates the number of MKPDUs received which contain an MN that is not
                                     acceptably recent.";
                            }

                            leaf parameter-not-quad-size {
                                status obsolete;
                                type yang:counter64;
                                description
                                    "Indicates the number of MKPDUs received which contain a parameter set that is
                                     not a multiple of 4 octets.";
                            }

                            leaf unsupported-algorithm-agility {
                                status obsolete;
                                type yang:counter64;
                                description
                                    "Indicates the number of MKPDUs received which contain an unsupported Algorithm
                                     Agility value.";
                            }

                            leaf invalid-ckn-length {
                                status obsolete;
                                type yang:counter64;
                                description
                                    "Indicates the number of MKPDUs received which contain a CAK name that exceeds
                                     the maximum CAK name length.";
                            }

                            leaf icv-check-failed {
                                status obsolete;
                                type yang:counter64;
                                description
                                    "Indicates the number of MKPDUs received which contain an ICV value that does
                                     not authenticate.";
                            }

                            leaf peer-same-mi {
                                status obsolete;
                                type yang:counter64;
                                description
                                    "Indicates the number of MKPDUs received which contain a peerlist with an MI
                                     entry which conflicts with the local MI.";
                            }

                            leaf sak-non-live-peer {
                                status obsolete;
                                type yang:counter64;
                                description
                                    "Indicates the number of SAKs received from a peer that is not a member of the
                                     Live Peers List.";
                            }

                            leaf sak-no-key-server {
                                status obsolete;
                                type yang:counter64;
                                description
                                    "Indicates the number of SAKs received from an MKA participant that has not
                                     been designated as the Key Server.";
                            }

                            leaf sak-decrypt-fail {
                                status obsolete;
                                type yang:counter64;
                                description
                                    "Indicates the number of AES Key Wrap SAK decryption failures that have
                                     occurred.";
                            }

                            leaf sak-encrypt-fail {
                                status obsolete;
                                type yang:counter64;
                                description
                                    "Indicates the number of AES Key Wrap SAK encryption failures that have
                                     occurred.";
                            }

                            leaf key-number-invalid {
                                status obsolete;
                                type yang:counter64;
                                description "Indicates the number of SAKs received with an invalid Key Number.";
                            }

                            leaf sak-install-fail {
                                status obsolete;
                                type yang:counter64;
                                description "Indicates the number of SecY SAK installation failures that have occurred.";
                            }

                            leaf cak-info-missing {
                                status obsolete;
                                type yang:counter64;
                                description
                                    "Indicates the number of times internal CAK data is not available for the
                                     generation of the SAK.";
                            }

                            leaf max-peers-set-zero {
                                status obsolete;
                                type yang:counter64;
                                description
                                    "Indicates the number of SecY SAK installations that have failed due to the max
                                     peer entry being set to 0.";
                            }

                            leaf oper-state {
                                status obsolete;
                                type types-sros:oper-state;
                                description "Indicates the operational state of the MKA participant.";
                            }

                            leaf oper-offset {
                                status obsolete;
                                type uint32 {
                                    range "0|30|50";
                                }
                                units "octets";
                                description
                                    "Indicates the operational encryption offset used for the datapath PDUs when
                                     all parties in the CA have the SAK. This value is specified by the key
                                     server.";
                            }

                            leaf oper-cipher {
                                status obsolete;
                                type enumeration {
                                    enum gcm-aes-128                    { value 1; }
                                    enum gcm-aes-256                    { value 2; }
                                    enum gcm-aes-xpn-128                { value 3; }
                                    enum gcm-aes-xpn-256                { value 4; }
                                }
                                description
                                    "Indicates the operational encryption algorithm used for datapath PDUs when all
                                     parties in the CA have the SAK. This value is specified by the key server.";
                            }

                            leaf latest-sak-lpn {
                                status obsolete;
                                type yang:counter64;
                                description "Indicates Lowest Acceptable Packet Number of the latest SAK.";
                            }

                            leaf previous-sak-lpn {
                                status obsolete;
                                type yang:counter64;
                                description "Indicates Lowest Acceptable Packet Number of the previous SAK.";
                            }

                            leaf invalid-header {
                                status obsolete;
                                type yang:counter64;
                                description "Indicates the number of MKPDUs received with an invalid MKA header.";
                            }

                            leaf cak-name {
                                status obsolete;
                                type types-security:cak-name;
                                description "Indicates the name of the CAK in use by this MKA.";
                            }

                            leaf transmit-interval {
                                status obsolete;
                                type uint32;
                                units "milliseconds";
                                description
                                    "Indicates the time interval at which the MKA broadcasts its liveliness to its
                                     peers.";
                            }

                            leaf key-server-priority {
                                status obsolete;
                                type uint32;
                                description "Indicates the priority of this MKA.";
                            }

                            leaf principal {
                                status obsolete;
                                type boolean;
                                description "Indicates whether this MKA session is the principal session.";
                            }

                            leaf encoding-an {
                                status obsolete;
                                type union {
                                    type int32 {
                                        range "0..3";
                                    }
                                    type enumeration {
                                        enum none                           { value -1; }
                                    }
                                }
                                description
                                    "Indicates the Association Number (AN) of the SA currently used to encode the
                                     SecTAG for frames awaiting transmission.";
                            }

                            leaf latest-sak-receiving {
                                status obsolete;
                                type boolean;
                                description
                                    "Indicates whether reception for the SAK is enabled for all the receive SAs
                                     identified by the AN of the latest SAK";
                            }

                            leaf latest-sak-transmitting {
                                status obsolete;
                                type boolean;
                                description
                                    "Indicates whether the SecY is transmitting using the SAK and its own SA with the
                                     AN identified by the AN of the latest SAK.";
                            }

                            leaf previous-sak-receiving {
                                status obsolete;
                                type boolean;
                                description
                                    "Indicates whether reception for the SAK is enabled for all the receive SAs
                                     identified by the AN of the previous SAK.";
                            }

                            leaf previous-sak-transmitting {
                                status obsolete;
                                type boolean;
                                description
                                    "Indicates whether the SecY is transmitting using the SAK and its own SA with the
                                     AN identified bby the AN of the previous SAK.";
                            }

                            leaf psk-source {
                                status obsolete;
                                type types-security:psk-source;
                                description "The source of the PSK.";
                            }

                            leaf unexpected-distributed-cak {
                                status obsolete;
                                type yang:counter64;
                                description "Indicates the number of discarded distributed CAKs.";
                            }

                            leaf unexpected-distributed-sak {
                                status obsolete;
                                type yang:counter64;
                                description "Indicates the number of discarded distributed SAKs.";
                            }

                        } // list mka

                    } // list peer

                } // list encryption-group

            } // container tunnel-encryption

            container service-encryption {
                status obsolete;
                description "Enter the service-encryption context";

                list encryption-group {
                    status obsolete;
                    key "group-name";
                    description "Enter the encryption-group list instance";

                    leaf group-name {
                        status obsolete;
                        type types-sros:named-item;
                        description "ANYsec encryption group name";
                    }

                    leaf group-id {
                        status obsolete;
                        type uint32;
                        description "Encryption group ID";
                    }

                    list peer {
                        status obsolete;
                        key "peer-ip-address";
                        description "Enter the peer list instance";

                        leaf peer-ip-address {
                            status obsolete;
                            type types-sros:ip-unicast-address;
                            description "Peer IP address";
                        }

                        leaf encryption-label {
                            status obsolete;
                            type types-sros:mpls-label-full-range;
                            description "The label uniquely identifying packets sent from this peer";
                        }

                        leaf last-inconsistent-rx-sci {
                            status obsolete;
                            type binary {
                                length "8";
                            }
                            description "The last inconsistent Rx SCI received from this peer";
                        }

                        leaf oper-state {
                            status obsolete;
                            type types-sros:oper-state;
                            description "Peer operational state";
                        }

                        leaf oper-down-reason {
                            status obsolete;
                            type enumeration {
                                enum none                           { value 0; }
                                enum peer-admin-down                { value 1; }
                                enum encrypt-group-admin-down       { value 2; }
                                enum term-policy-admin-down         { value 3; }
                                enum ca-admin-down                  { value 4; }
                                enum mka-down                       { value 5; }
                                enum inconsistent-rx-sci            { value 6; }
                                enum missing-rx-tunnel              { value 7; }
                                enum missing-tx-tunnel              { value 8; }
                            }
                            description "Peer operational state down reason";
                        }

                        container rx-sc {
                            status obsolete;
                            description "Enter the rx-sc context";

                            leaf rx-sci {
                                status obsolete;
                                type binary {
                                    length "8";
                                }
                                description "Indicates the SCI for identifying the receiving SC.";
                            }

                            leaf not-valid-packets {
                                status obsolete;
                                type yang:counter64;
                                units "packets";
                                description "Indicates the number of not valid packets received by this SC.";
                            }

                            leaf delayed-packets {
                                status obsolete;
                                type yang:counter64;
                                units "packets";
                                description
                                    "Indicates the number of received packets with the condition that the PN of the
                                     packets is lower than the lower bound of the replay protection PN.";
                            }

                            leaf unchecked-packets {
                                status obsolete;
                                type yang:counter64;
                                units "packets";
                                description
                                    "Indicates the number of packets that have failed the integrity check on this
                                     SC.";
                            }

                            leaf ok-packets {
                                status obsolete;
                                type yang:counter64;
                                units "packets";
                                description "Indicates the number of OK packets received by this SC.";
                            }

                            leaf octets-decrypted {
                                status obsolete;
                                type yang:counter64;
                                units "octets";
                                description
                                    "Indicates the number of octets of plain text recovered from received packets
                                     that were integrity protected and encrypted.";
                            }

                        } // container rx-sc

                        container tx-sc {
                            status obsolete;
                            description "Enter the tx-sc context";

                            leaf tx-sci {
                                status obsolete;
                                type binary {
                                    length "8";
                                }
                                description
                                    "Indicates the Secure Channel Identifier (SCI) information for transmitting
                                     ANYsec MACsec frames. This is the same value as
                                     /state/anysec/tunnel-encryption/encryption-group/peer/mka/outbound-sci";
                            }

                            leaf encrypted-packets {
                                status obsolete;
                                type yang:counter64;
                                units "packets";
                                description
                                    "Indicates the number of integrity protected and encrypted packets for this
                                     transmitting SC.";
                            }

                            leaf octets-encrypted {
                                status obsolete;
                                type yang:counter64;
                                units "octets";
                                description
                                    "Indicates the number of plain text octets that are integrity protected and
                                     encrypted on the transmitting SC.";
                            }

                        } // container tx-sc

                        list mka {
                            status obsolete;
                            key "ckn";
                            description "Enter the mka list instance";

                            leaf ckn {
                                status obsolete;
                                type binary {
                                    length "1..32";
                                }
                                description "Indicates CKN information for the MKA instance.";
                            }

                            leaf member-id {
                                status obsolete;
                                type binary {
                                    length "12";
                                }
                                description "Indicates the Member Identifier (MI) for the MKA instance.";
                            }

                            leaf outbound-sci {
                                status obsolete;
                                type binary {
                                    length "8";
                                }
                                description
                                    "Indicates the Secure Channel Identifier (SCI) information for transmitting
                                     ANYsec MACsec frames.";
                            }

                            leaf message-count {
                                status obsolete;
                                type uint32;
                                description "Indicates the current count of MKA messages that is attached to MKA PDUs.";
                            }

                            leaf key-number {
                                status obsolete;
                                type uint32;
                                description
                                    "Indicates the number of the currently assigned CAK. When a new CAK is
                                     generated, this number is incremented.";
                            }

                            leaf key-server {
                                status obsolete;
                                type boolean;
                                description
                                    "Indicates whether this server is the highest priority server in the peer
                                     group.";
                            }

                            leaf latest-sak-an {
                                status obsolete;
                                type uint32;
                                description
                                    "Indicates the Association Number (AN) of the latest Secure Association Key
                                     (SAK). This number is concatenated with an SCI to identify a Secure
                                     Association (SA).";
                            }

                            leaf previous-sak-an {
                                status obsolete;
                                type uint32;
                                description
                                    "Indicates the AN of the previous SAK. This number is concatenated with an SCI
                                     to identify an SA.";
                            }

                            leaf latest-sak-ki {
                                status obsolete;
                                type binary {
                                    length "16";
                                }
                                description
                                    "Indicates the Key Identifier (KI) of the latest SAK. This number is derived
                                     from the MI of the key server and the key number.";
                            }

                            leaf previous-sak-ki {
                                status obsolete;
                                type binary {
                                    length "16";
                                }
                                description
                                    "Indicates the KI of the previous SAK. This number is derived from the MI of
                                     the key server and the key number.";
                            }

                            leaf peers-removed {
                                status obsolete;
                                type yang:counter64;
                                description
                                    "Indicates the number of peers removed from the live/potential peer list due to
                                     not receiving an MKPDU within the MKA Live Time (6.0 sec).";
                            }

                            leaf ckn-not-found {
                                status obsolete;
                                type yang:counter64;
                                description
                                    "Indicates the number of MKPDUs received with a CKN that does not match the CA
                                     configured for the port.";
                            }

                            leaf new-live-peer {
                                status obsolete;
                                type yang:counter64;
                                description
                                    "Indicates the number of validated peers that have been added to the live peer
                                     list.";
                            }

                            leaf sak-generated {
                                status obsolete;
                                type yang:counter64;
                                description "Indicates the number of SAKs generated by this MKA instance.";
                            }

                            leaf sak-installed-transmitting {
                                status obsolete;
                                type yang:counter64;
                                description "Indicates the number of SAKs installed for transmitting.";
                            }

                            leaf sak-installed-receiving {
                                status obsolete;
                                type yang:counter64;
                                description "Indicates the number of SAKs installed for receiving.";
                            }

                            leaf pdu-too-small {
                                status obsolete;
                                type yang:counter64;
                                description "Indicates the number of MKPDUs received that are less than 32 octets.";
                            }

                            leaf pdu-too-big {
                                status obsolete;
                                type yang:counter64;
                                description
                                    "Indicates the number of MKPDUs received where the EAPOL header indicates a
                                     size larger than the received packet.";
                            }

                            leaf pdu-not-quad-size {
                                status obsolete;
                                type yang:counter64;
                                description
                                    "Indicates the number of MKPDUs received with a size that is not a multiple of
                                     4 octets.";
                            }

                            leaf pdu-invalid-number {
                                status obsolete;
                                type yang:counter64;
                                description
                                    "Indicates the number of MKPDUs received out of order as indicated by the
                                     Message Number.";
                            }

                            leaf parameter-size-invalid {
                                status obsolete;
                                type yang:counter64;
                                description
                                    "Indicates the number of MKPDUs received which contain a parameter set body
                                     length that exceeds the remaining length of the MKPDU.";
                            }

                            leaf liveness-check-fail {
                                status obsolete;
                                type yang:counter64;
                                description
                                    "Indicates the number of MKPDUs received which contain an MN that is not
                                     acceptably recent.";
                            }

                            leaf parameter-not-quad-size {
                                status obsolete;
                                type yang:counter64;
                                description
                                    "Indicates the number of MKPDUs received which contain a parameter set that is
                                     not a multiple of 4 octets.";
                            }

                            leaf unsupported-algorithm-agility {
                                status obsolete;
                                type yang:counter64;
                                description
                                    "Indicates the number of MKPDUs received which contain an unsupported Algorithm
                                     Agility value.";
                            }

                            leaf invalid-ckn-length {
                                status obsolete;
                                type yang:counter64;
                                description
                                    "Indicates the number of MKPDUs received which contain a CAK name that exceeds
                                     the maximum CAK name length.";
                            }

                            leaf icv-check-failed {
                                status obsolete;
                                type yang:counter64;
                                description
                                    "Indicates the number of MKPDUs received which contain an ICV value that does
                                     not authenticate.";
                            }

                            leaf peer-same-mi {
                                status obsolete;
                                type yang:counter64;
                                description
                                    "Indicates the number of MKPDUs received which contain a peerlist with an MI
                                     entry which conflicts with the local MI.";
                            }

                            leaf sak-non-live-peer {
                                status obsolete;
                                type yang:counter64;
                                description
                                    "Indicates the number of SAKs received from a peer that is not a member of the
                                     Live Peers List.";
                            }

                            leaf sak-no-key-server {
                                status obsolete;
                                type yang:counter64;
                                description
                                    "Indicates the number of SAKs received from an MKA participant that has not
                                     been designated as the Key Server.";
                            }

                            leaf sak-decrypt-fail {
                                status obsolete;
                                type yang:counter64;
                                description
                                    "Indicates the number of AES Key Wrap SAK decryption failures that have
                                     occurred.";
                            }

                            leaf sak-encrypt-fail {
                                status obsolete;
                                type yang:counter64;
                                description
                                    "Indicates the number of AES Key Wrap SAK encryption failures that have
                                     occurred.";
                            }

                            leaf key-number-invalid {
                                status obsolete;
                                type yang:counter64;
                                description "Indicates the number of SAKs received with an invalid Key Number.";
                            }

                            leaf sak-install-fail {
                                status obsolete;
                                type yang:counter64;
                                description "Indicates the number of SecY SAK installation failures that have occurred.";
                            }

                            leaf cak-info-missing {
                                status obsolete;
                                type yang:counter64;
                                description
                                    "Indicates the number of times internal CAK data is not available for the
                                     generation of the SAK.";
                            }

                            leaf max-peers-set-zero {
                                status obsolete;
                                type yang:counter64;
                                description
                                    "Indicates the number of SecY SAK installations that have failed due to the max
                                     peer entry being set to 0.";
                            }

                            leaf oper-state {
                                status obsolete;
                                type types-sros:oper-state;
                                description "Indicates the operational state of the MKA participant.";
                            }

                            leaf oper-offset {
                                status obsolete;
                                type uint32 {
                                    range "0|30|50";
                                }
                                units "octets";
                                description
                                    "Indicates the operational encryption offset used for the datapath PDUs when
                                     all parties in the CA have the SAK. This value is specified by the key
                                     server.";
                            }

                            leaf oper-cipher {
                                status obsolete;
                                type enumeration {
                                    enum gcm-aes-128                    { value 1; }
                                    enum gcm-aes-256                    { value 2; }
                                    enum gcm-aes-xpn-128                { value 3; }
                                    enum gcm-aes-xpn-256                { value 4; }
                                }
                                description
                                    "Indicates the operational encryption algorithm used for datapath PDUs when all
                                     parties in the CA have the SAK. This value is specified by the key server.";
                            }

                            leaf latest-sak-lpn {
                                status obsolete;
                                type yang:counter64;
                                description "Indicates Lowest Acceptable Packet Number of the latest SAK.";
                            }

                            leaf previous-sak-lpn {
                                status obsolete;
                                type yang:counter64;
                                description "Indicates Lowest Acceptable Packet Number of the previous SAK.";
                            }

                            leaf invalid-header {
                                status obsolete;
                                type yang:counter64;
                                description "Indicates the number of MKPDUs received with an invalid MKA header.";
                            }

                            leaf cak-name {
                                status obsolete;
                                type types-security:cak-name;
                                description "Indicates the name of the CAK in use by this MKA.";
                            }

                            leaf transmit-interval {
                                status obsolete;
                                type uint32;
                                units "milliseconds";
                                description
                                    "Indicates the time interval at which the MKA broadcasts its liveliness to its
                                     peers.";
                            }

                            leaf key-server-priority {
                                status obsolete;
                                type uint32;
                                description "Indicates the priority of this MKA.";
                            }

                            leaf principal {
                                status obsolete;
                                type boolean;
                                description "Indicates whether this MKA session is the principal session.";
                            }

                            leaf encoding-an {
                                status obsolete;
                                type union {
                                    type int32 {
                                        range "0..3";
                                    }
                                    type enumeration {
                                        enum none                           { value -1; }
                                    }
                                }
                                description
                                    "Indicates the Association Number (AN) of the SA currently used to encode the
                                     SecTAG for frames awaiting transmission.";
                            }

                            leaf latest-sak-receiving {
                                status obsolete;
                                type boolean;
                                description
                                    "Indicates whether reception for the SAK is enabled for all the receive SAs
                                     identified by the AN of the latest SAK";
                            }

                            leaf latest-sak-transmitting {
                                status obsolete;
                                type boolean;
                                description
                                    "Indicates whether the SecY is transmitting using the SAK and its own SA with the
                                     AN identified by the AN of the latest SAK.";
                            }

                            leaf previous-sak-receiving {
                                status obsolete;
                                type boolean;
                                description
                                    "Indicates whether reception for the SAK is enabled for all the receive SAs
                                     identified by the AN of the previous SAK.";
                            }

                            leaf previous-sak-transmitting {
                                status obsolete;
                                type boolean;
                                description
                                    "Indicates whether the SecY is transmitting using the SAK and its own SA with the
                                     AN identified bby the AN of the previous SAK.";
                            }

                            leaf psk-source {
                                status obsolete;
                                type types-security:psk-source;
                                description "The source of the PSK.";
                            }

                            leaf unexpected-distributed-cak {
                                status obsolete;
                                type yang:counter64;
                                description "Indicates the number of discarded distributed CAKs.";
                            }

                            leaf unexpected-distributed-sak {
                                status obsolete;
                                type yang:counter64;
                                description "Indicates the number of discarded distributed SAKs.";
                            }

                        } // list mka

                    } // list peer

                } // list encryption-group

            } // container service-encryption

        } // container anysec

    } // grouping state-anysec

}
