submodule nokia-state-lag {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-lldp               { prefix "types-lldp"; }
    import nokia-types-qos                { prefix "types-qos"; }
    import nokia-types-sros               { prefix "types-sros"; }
    import nokia-types-subscriber-mgmt    { prefix "types-submgt"; }

    include nokia-state-eth-cfm;
    include nokia-state-port;

    sros-ext:sros-major-release "rel26";
    organization "Nokia";
    contact
        "Nokia SR OS Support
         Web: <http://www.nokia.com>";
    description
        "Nokia YANG Data model with operational state for link aggregation group on SR OS based routers.

         Copyright 2016 Nokia. All rights reserved. Reproduction of this document
         is authorized on the condition that the foregoing copyright notice is included.

         This nokia-state-lag YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping state-lag {
        list lag {
            key "lag-name";
            description "Enter the lag list instance";

            leaf lag-name {
                type types-sros:lag-interface;
                description "LAG Name always to start with lag-";
            }

            leaf lag-id {
                type uint32;
                description "internal lag-id";
            }

            leaf oper-state {
                type types-sros:oper-state;
                description "Operational state of the LAG.";
            }

            leaf lacp-admin-key-autogen {
                type boolean;
                description
                    "lacp-admin-key-autogen is set to 'true' if the LAG administrative key
                     in the lag-configwas auto generated.
                     lacp-admin-key-autogen is set to 'false', if the LAG administrative
                     key was manually configured.";
            }

            leaf threshold-rising {
                type yang:counter32;
                description
                    "counts the number of linkUp or dynamic/static-cost events for the
                     LAG caused by the number of physical ports
                     being greater than tLagPortThreshold value.";
            }

            leaf threshold-falling {
                type yang:counter32;
                description
                    "counts the number of linkDown or dynamic/static-cost events for the
                     LAG caused by the number of physical ports
                     being less or equal than tLagPortThreshold value.";
            }

            leaf if-index {
                type uint32;
                description "ifIndex for the LAG.";
            }

            leaf hardware-mac-address {
                type yang:mac-address;
                description "System generated MAC address for the LAG.";
            }

            leaf forced {
                type enumeration {
                    enum not-appl                       { value 0; }
                    enum active                         { value 1; }
                    enum standby                        { value 2; }
                }
                description "Selection state forced by the tools command";
            }

            leaf available-bandwidth {
                type yang:counter64;
                units "kilobps";
                description "The administrative bandwidth that is still free for booking on this LAG.";
            }

            leaf booked-bandwidth {
                type yang:counter64;
                units "kilobps";
                description "The administrative bandwidth that has been booked.";
            }

            leaf remaining-hold-time {
                type union {
                    type int32 {
                        range "0..2000";
                    }
                    type enumeration {
                        enum infinite                       { value -1; }
                    }
                }
                units "deciseconds";
                description
                    "The value indicates the time
                     remaining before this system would switch to the newly
                     eligible sub-group.
                     The value zero indicates that the system would immediately switch
                     back.
                     The value all ones indicates that the system would never switch
                     back autonomously.";
            }

            leaf selected-sub-group {
                type union {
                    type uint32 {
                        range "0..16";
                    }
                    type enumeration {
                        enum mc-peer                        { value -1; }
                    }
                }
                description
                    "This value indicates
                     the currently selected sub-group.

                     The value zero indicates that the value is not applicable.

                     The value minus one can appear in a multi-chassis LAG configuration
                     and indicates that the selected sub-group is in
                     the scope of the multi-chassis peer.";
            }

            leaf candidate-sub-group {
                type union {
                    type uint32 {
                        range "1..16";
                    }
                    type enumeration {
                        enum mc-peer                        { value -1; }
                    }
                }
                description
                    "This value indicates
                     the candidate sub-group.

                     The value zero indicates that the value is not applicable.

                     The value minus one can appear in a multi-chassis LAG configuration
                     and indicates that the candidate sub-group is in
                     the scope of the multi-chassis peer.";
            }

            leaf sub-group-count {
                type uint32;
                description
                    "This value indicates the number of subgroups
                     configured in this LAG.";
            }

            leaf operational-key {
                type int32 {
                    range "0..65535";
                }
                description "LACP operational key";
            }

            leaf system-id {
                type yang:mac-address;
                description "LACP system identifier.";
            }

            leaf system-priority {
                type int32 {
                    range "0..65535";
                }
                description "LACP system priority.";
            }

            leaf partner-system-id {
                type yang:mac-address;
                description "LACP partner system identifier.";
            }

            leaf partner-priority {
                type int32 {
                    range "0..65535";
                }
                description "LACP partner priority.";
            }

            leaf partner-operational-key {
                type int32 {
                    range "0..65535";
                }
                description "LACP partner operational key";
            }

            leaf number-weight-up {
                type yang:gauge32;
                description
                    "This value indicates
                     the weight of the physical ports that are operational (link up).";
            }

            leaf bandwidth {
                type yang:gauge64;
                description
                    "This value indicates
                     the bandwidth of the lag.";
            }

            leaf number-port-up {
                type yang:gauge32;
                description
                    "This value indicates
                     the number of physical ports that are operational (link up).";
            }

            leaf total-weight {
                type yang:gauge32;
                description "This value indicates the total weight of the physical ports.";
            }

            leaf adaptive-load-balancing-number-rebalance {
                type yang:gauge32;
                description "This value indicates the total number of rebalances.";
            }

            leaf adaptive-load-balancing-diff-most-least-loaded-link {
                type types-sros:percent {
                    range "0..100";
                }
                description "This value indicates the diff in percentage between the most and least loaded link.";
            }

            leaf lacp-fallback-time-remaining {
                type int32;
                units "seconds";
                description
                    "The value indicates the time remaining for LACP
                     fallback mode to become active.
                     It is reset to the configured fallback timeout value
                     whenever a LACP PDU is received.";
            }

            container network {
                description "Enter the network context";

                container egress {
                    description "Enter the egress context";

                    list queue {
                        key "queue-id";
                        description "Enter the queue list instance";

                        leaf queue-id {
                            type types-qos:ingress-queue-id;
                            description "Specifies the ingress queue group queue identifier.";
                        }

                        container statistics {
                            description "Enter the statistics context";

                            leaf in-profile-forwarded-packets {
                                type yang:counter64;
                                description "The number of in-inplus profile forwarded packets.";
                            }

                            leaf in-profile-forwarded-octets {
                                type yang:counter64;
                                description "The number of in-inplus profile forwarded octets.";
                            }

                            leaf in-profile-dropped-packets {
                                type yang:counter64;
                                description "The number of in-inplus profile dropped packets.";
                            }

                            leaf in-profile-dropped-octets {
                                type yang:counter64;
                                description "The number of in-inplus profile dropped octets.";
                            }

                            leaf out-profile-forwarded-packets {
                                type yang:counter64;
                                description "The number of out-exceed profile forwarded packets.";
                            }

                            leaf out-profile-forwarded-octets {
                                type yang:counter64;
                                description "The number of out-exceed profile forwarded octets.";
                            }

                            leaf out-profile-dropped-packets {
                                type yang:counter64;
                                description "The number of out-exceed profile dropped packets.";
                            }

                            leaf out-profile-dropped-octets {
                                type yang:counter64;
                                description "The number of out-exceed profile dropped octets.";
                            }

                        } // container statistics

                    } // list queue

                } // container egress

                container ingress {
                    description "Enter the ingress context";

                    list queue {
                        key "queue-id";
                        description "Enter the queue list instance";

                        leaf queue-id {
                            type types-qos:ingress-queue-id;
                            description "Specifies the ingress queue group queue identifier.";
                        }

                        container statistics {
                            description "Enter the statistics context";

                            leaf in-profile-forwarded-packets {
                                type yang:counter64;
                                description "The number of in-inplus profile forwarded packets.";
                            }

                            leaf in-profile-forwarded-octets {
                                type yang:counter64;
                                description "The number of in-inplus profile forwarded octets.";
                            }

                            leaf in-profile-dropped-packets {
                                type yang:counter64;
                                description "The number of in-inplus profile dropped packets.";
                            }

                            leaf in-profile-dropped-octets {
                                type yang:counter64;
                                description "The number of in-inplus profile dropped octets.";
                            }

                            leaf out-profile-forwarded-packets {
                                type yang:counter64;
                                description "The number of out-exceed profile forwarded packets.";
                            }

                            leaf out-profile-forwarded-octets {
                                type yang:counter64;
                                description "The number of out-exceed profile forwarded octets.";
                            }

                            leaf out-profile-dropped-packets {
                                type yang:counter64;
                                description "The number of out-exceed profile dropped packets.";
                            }

                            leaf out-profile-dropped-octets {
                                type yang:counter64;
                                description "The number of out-exceed profile dropped octets.";
                            }

                        } // container statistics

                    } // list queue

                } // container ingress

            } // container network

            container multi-chassis {
                description "Enter the multi-chassis context";

                leaf active-standby {
                    type enumeration {
                        enum active                         { value 1; }
                        enum stand-by                       { value 2; }
                    }
                    description "Indicates active standby state of the MC-LAG.";
                }

                leaf selection-reason {
                    type types-sros:display-string-or-empty {
                        length "0..255";
                    }
                    description "Selection reason";
                }

                leaf config-mismatch-reason {
                    type types-sros:display-string-or-empty {
                        length "0..255";
                    }
                    description "Configuration mismatch reason";
                }

                leaf extended-timeout {
                    type boolean;
                    description "Extended timeout";
                }

            } // container multi-chassis

            container eth-cfm {
                description "Enter the eth-cfm context";

                list mep {
                    key "md-admin-name ma-admin-name mep-id";
                    description "Enter the mep list instance";

                    leaf md-admin-name {
                        type leafref {
                            path "../../../../eth-cfm/domain/md-admin-name";
                        }
                        description "A unique administratively assigned name used to identify a domain.";
                    }

                    leaf ma-admin-name {
                        type leafref {
                            path "../../../../eth-cfm/domain[md-admin-name=current()/../md-admin-name]/association/ma-admin-name";
                        }
                        description "A unique administratively assigned name used to identify an association.";
                    }

                    leaf mep-id {
                        type types-eth-cfm:mep-id-type;
                        description
                            "A CFM Virtual Maintenance Endpoint

                             Specifies a local Maintenance association End Point identifier unique
                             over a given maintanance association.";
                    }

                    leaf if-index {
                        type uint32;
                        description "Port ID of the MEP.";
                    }

                    leaf oper-mac-address {
                        type yang:mac-address;
                        description "Operational MAC address of the MEP.";
                    }

                    container ais {
                        description "Enter the ais context";

                        container received {
                            description "Enter the received context";

                            leaf ais-packet {
                                type boolean;
                                description "Indicates if the MEP is receiving AIS test frames from one or more of its sub-layer MEPs.";
                            }

                            leaf interval {
                                type uint32 {
                                    range "1|60";
                                }
                                units "seconds";
                                description "Indicates the AIS Interval received in the last AIS Frame.";
                            }

                        } // container received

                        container transmitted {
                            description "Enter the transmitted context";

                            leaf ais-packet {
                                type enumeration {
                                    enum no-transmit                    { value 0; }
                                    enum transmit                       { value 1; }
                                    enum pending                        { value 2; }
                                }
                                description "Indicates if the MEP is transmitting AIS test frames from one or more of its sub-layer MEPs.";
                            }

                        } // container transmitted

                    } // container ais

                    container csf {
                        description "Enter the csf context";

                        container received {
                            description "Enter the received context";

                            leaf state {
                                type enumeration {
                                    enum los                            { value 0; }
                                    enum ais                            { value 1; }
                                    enum rdi                            { value 2; }
                                    enum dci                            { value 3; }
                                }
                                description
                                    "Indicates the state of the received CSF frames for the MEP.
                                        los (0) - Client Loss of Signal
                                        ais (1) - Client Forward Defect Indication
                                        rdi (2) - Client Reverse Defect Indication
                                        dci (3) - Client Defect Clear Indication.";
                            }

                            leaf interval {
                                type uint32 {
                                    range "1|60";
                                }
                                units "seconds";
                                description "Indicates the CSF Interval received in the most recent CSF frame.";
                            }

                        } // container received

                    } // container csf

                    container grace {
                        description "Enter the grace context";

                        container transmitted {
                            description "Enter the transmitted context";

                            leaf grace-notification {
                                type enumeration {
                                    enum no-transmit                    { value 0; }
                                    enum grace                          { value 1; }
                                    enum eth-ed                         { value 2; }
                                }
                                description "Indicates the state of the MEP grace period PDU transmission.";
                            }

                        } // container transmitted

                        container received {
                            description "Enter the received context";

                            leaf process-grace-notification {
                                type boolean;
                                description
                                    "Indicates whether the local MEP is receiving and processing grace notifications
                                     from one or more peer MEPs. A value of 'true ' indicates the local MEP is
                                     receiving and processing grace from at least one peer MEP. A value
                                     of 'false' indicates that no peer grace notifications are being
                                     received and processed.";
                            }

                        } // container received

                    } // container grace

                    container ccm-states {
                        description "Enter the ccm-states context";

                        leaf transmit-status {
                            type enumeration {
                                enum no-transmit                    { value 0; }
                                enum transmit                       { value 1; }
                                enum suppressed                     { value 2; }
                            }
                            description
                                "Indicates the state of the MEP CCM PDU transmission.

                                 Values:
                                    noTransmit (0) - no CCM PDUs are being transmitted by the MEP
                                    transmit   (1) - MEP is currently transmitting CCM PDUs
                                    suppressed (2) - MEP should be transmitting CCM PDUs but is suppressing
                                                    them due to an internal condition";
                        }

                        leaf sequence-error {
                            type yang:counter32;
                            description "The total number of out-of-sequence CCMs received from all remote MEPs.";
                        }

                        leaf fng-state {
                            type types-eth-cfm:fng-state-type;
                            description "Current state of the MEP Fault Notification Generator State Machine.";
                        }

                        container transmitted {
                            description "Enter the transmitted context";

                            leaf count {
                                type yang:counter32;
                                description "Total number of CCMs transmitted.";
                            }

                            leaf interface-status {
                                type types-eth-cfm:interface-status;
                                description
                                    "Indicates the interface status TLV information included in the most
                                     recent Connectivity Check Message (CCM) transmission from the local MEP.
                                     If the local MEP CCM transmissions are not enabled, or if no interface
                                     status TLV was included in the most recent transmission, then
                                     ccm-tx-if-status will return a value of is-no-interface-status-tlv (0).";
                            }

                            leaf port-status {
                                type types-eth-cfm:port-status;
                                description
                                    "Indicates the port status TLV information included in the most recent
                                     Connectivity Check Message (CCM) transmission from the local MEP.

                                     If the local MEP CCM transmissions are not enabled, or if no port
                                     status TLV was included in the most recent transmission, then
                                     ccm-tx-port-status will return a value of ps-no-port-state-tlv (0).";
                            }

                            leaf remote-defect-indicator {
                                type boolean;
                                description
                                    "Indicates whether or not the Remote Defect Indication (RDI) bit was set
                                     on the most recent Connectivity Check Message (CCM) transmission from the
                                     local MEP.

                                     If the local MEP CCM transmissions are not eanbled, or if the RDI bit
                                     was not set in the most recent transmission, then ccm-tx-rdi will return
                                     a value of 'false (2)'.";
                            }

                        } // container transmitted

                        container received {
                            description "Enter the received context";

                            leaf highest-priority-defect {
                                type types-eth-cfm:highest-priority-defect-type;
                                description
                                    "The highest priority defect that has been present since the
                                     MEPs Fault Notification Generator State Machine was last in
                                     the reset state.";
                            }

                            leaf defect-flags {
                                type types-eth-cfm:mep-defect-flags;
                                description "A vector of boolean error conditions, any of which may be true.";
                            }

                            list remote-mep-peer {
                                key "remote-mep-id";
                                description "Enter the remote-mep-peer list instance";

                                leaf remote-mep-id {
                                    type types-eth-cfm:mep-id-type;
                                    description "The Remote MEP ID within the same Maintenance Association.";
                                }

                                leaf auto-discovered {
                                    type boolean;
                                    description
                                        "Specifies whether or not the remote peer was automatically discovered
                                         ('true') or not. Auto-discovered remote peers are created by the system
                                         only, and are of a 'volatile' storage type. Specifying the value of
                                         'false' will mark an auto-discovered remote peer as permanently configured.";
                                }

                                leaf receiving-ccm {
                                    type types-eth-cfm:remote-mep-state-type;
                                    description "The operational CCM receiving state of the remote MEP.";
                                }

                                leaf ccm-status-since {
                                    type yang:date-and-time;
                                    description
                                        "The time at which the Remote MEP
                                         last entered either the mep-failed or mep-ok state. ";
                                }

                                leaf peer-mac-address {
                                    type yang:mac-address;
                                    description "The MAC address of the remote MEP.";
                                }

                                leaf receiving-remote-defect-indicator {
                                    type boolean;
                                    description
                                        "State of the RDI bit in the last received CCM (true for rdi=1), or false
                                         if none has been received.";
                                }

                                leaf port-status-tlv {
                                    type types-eth-cfm:port-status;
                                    description
                                        "An enumerated value of the Port status TLV received in the
                                         last CCM from the remote MEP or the default value
                                         ps-no-port-state-tlv indicating either no CCM has been received,
                                         or that no port status TLV was received in the last CCM. ";
                                }

                                leaf interface-status-tlv {
                                    type types-eth-cfm:interface-status;
                                    description
                                        "An enumerated value of the Interface status TLV received
                                         in the last CCM from the remote MEP or the default value
                                         is-no-interface-status-tlv indicating either no CCM has been
                                         received, or that no interface status TLV was received in
                                         the last CCM.";
                                }

                            } // list remote-mep-peer

                        } // container received

                    } // container ccm-states

                    container mc-lag {
                        description "Enter the mc-lag context";

                        leaf inactive-state {
                            type enumeration {
                                enum not-applicable                 { value 0; }
                                enum standby                        { value 1; }
                                enum active                         { value 2; }
                            }
                            description
                                "Indicates the MC-LAG inactive state of the mep.  The value of
                                 system/eth-cfm/redundancy/mc-lag/standby-mep must be 'true (1)'
                                 on the node for this leaf to have meaning.";
                        }

                    } // container mc-lag

                    container statistics {
                        description "Enter the statistics context";

                        list opcode {
                            key "opcode-name";
                            description "Enter the opcode list instance";

                            leaf opcode-name {
                                type types-eth-cfm:statistics-opcode-name;
                                description "Integer that defines which CFM PDU Opcode the statictics refer to.";
                            }

                            leaf transmitted {
                                type yang:counter32;
                                description "The total number of PDUs transmitted from the node with the specified Opcode.";
                            }

                            leaf received {
                                type yang:counter32;
                                description "The total number of PDUs received on the node with the specified Opcode.";
                            }

                        } // list opcode

                    } // container statistics

                } // list mep

            } // container eth-cfm

            list port {
                key "port-id";
                description "Enter the port list instance";

                leaf port-id {
                    type leafref {
                        path "../../../port/port-id";
                    }
                    description "The identifier which uniquely identifies the port in the LAG.";
                }

                leaf active-standby {
                    type enumeration {
                        enum active                         { value 1; }
                        enum stand-by                       { value 2; }
                    }
                    description "Active/standby selection state of the port in the LAG.";
                }

                leaf oper-state {
                    status obsolete;
                    type types-sros:oper-state;
                    description
                        "Operational state of the member port.
                         This leaf was deprecated in release 21.10 on Nokia SROS series systems.
                         It is replaced by /state/port/oper-state.";
                }

                leaf primary {
                    type boolean;
                    description "Primary port indication.";
                }

                leaf forced {
                    type enumeration {
                        enum not-appl                       { value 0; }
                        enum active                         { value 1; }
                        enum standby                        { value 2; }
                    }
                    description "Selection state forced by the tools command";
                }

                leaf actor-oper-state {
                    type bits {
                        bit lacp-activity                  { position 0; }
                        bit lacp-timeout                   { position 1; }
                        bit aggregation                    { position 2; }
                        bit synchronization                { position 3; }
                        bit collecting                     { position 4; }
                        bit distributing                   { position 5; }
                        bit defaulted                      { position 6; }
                        bit expired                        { position 7; }
                    }
                    description "Actor states for LACP protocol.";
                }

                leaf partner-oper-state {
                    type bits {
                        bit lacp-activity                  { position 0; }
                        bit lacp-timeout                   { position 1; }
                        bit aggregation                    { position 2; }
                        bit synchronization                { position 3; }
                        bit collecting                     { position 4; }
                        bit distributing                   { position 5; }
                        bit defaulted                      { position 6; }
                        bit expired                        { position 7; }
                    }
                    description "Partner states for LACP protocol.";
                }

                leaf actor-port {
                    type int32;
                    description "Actor port for LACP protocol.";
                }

                leaf partner-port {
                    type int32;
                    description "Partner port for LACP protocol.";
                }

                leaf partner-port-priority {
                    type int32;
                    description "Partner port priority for LACP protocol.";
                }

                leaf adaptive-load-balancing-egress-rate {
                    type int64;
                    units "kilobps";
                    description "egress rate in kilobps";
                }

                leaf lacp-fallback-active {
                    type boolean;
                    description "LACP fallback port is active.";
                }

                container bfd {
                    description "Enter the bfd context";

                    leaf bfd-state {
                        type enumeration {
                            enum idle                           { value 0; }
                            enum failed                         { value 1; }
                            enum failed-fwd                     { value 2; }
                            enum waiting                        { value 3; }
                            enum waiting-fwd                    { value 4; }
                            enum up                             { value 5; }
                            enum down                           { value 6; }
                        }
                        description "The state of the micro-BFD session of this port in this LAG.";
                    }

                    leaf admin-down-time-left {
                        type uint32;
                        units "seconds";
                        description "The time left before this system will react upon the 'AdminDown' State indication.";
                    }

                    leaf setup-time-left {
                        type uint32;
                        units "milliseconds";
                        description "The set-up time left.";
                    }

                } // container bfd

                container lacp-statistics {
                    description "Enter the lacp-statistics context";

                    leaf rx-packets {
                        type yang:counter32;
                        description "number of valid lacp pdu packets received";
                    }

                    leaf tx-packets {
                        type yang:counter32;
                        description "number of valid lacp pdu packets transmitted";
                    }

                    leaf rx-illegal {
                        type yang:counter32;
                        description "number of illegal lacp pdu packets received";
                    }

                    leaf rx-errors {
                        type yang:counter32;
                        description "number of errornous lacp pdu packets received";
                    }

                    leaf tx-errors {
                        type yang:counter32;
                        description "number of errornous lacp pdu packets sent";
                    }

                } // container lacp-statistics

            } // list port

            list link-map-profile {
                key "link-map-profile-id";
                description "Enter the link-map-profile list instance";

                leaf link-map-profile-id {
                    type int32 {
                        range "1..64";
                    }
                    description "The LAG link map profile identifier.";
                }

                leaf active-link {
                    type types-sros:port;
                    description "The active link port for the link map profile.";
                }

            } // list link-map-profile

            container subscriber-management {
                description "Enter the subscriber-management context";

                container statistics {
                    description "Enter the statistics context";

                    leaf last-reset-peak-values {
                        type yang:date-and-time;
                        description "Timestamp of the last reset of the peak values";
                    }

                    list ipv4-hosts {
                        key "counter";
                        description "Enter the ipv4-hosts list instance";

                        leaf counter {
                            type types-submgt:submgt-statistics-ipv4-type;
                            description "Type of submgt ipv4 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv4-hosts

                    list ipv6-hosts {
                        key "counter";
                        description "Enter the ipv6-hosts list instance";

                        leaf counter {
                            type types-submgt:submgt-statistics-ipv6-type;
                            description "Type of submgt ipv6 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv6-hosts

                    list total-hosts {
                        key "counter";
                        description "Enter the total-hosts list instance";

                        leaf counter {
                            type types-submgt:submgt-statistics-total-type;
                            description "Type of submgt total hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list total-hosts

                    list sessions {
                        key "counter";
                        description "Enter the sessions list instance";

                        leaf counter {
                            type types-submgt:submgt-statistics-session-type;
                            description "Type of submgt sessions counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list sessions

                } // container statistics

                list svlan {
                    key "vlan-id";
                    description "Enter the svlan list instance";

                    leaf vlan-id {
                        type uint32 {
                            range "0..4094";
                        }
                        description "The VLAN identifier.";
                    }

                    leaf active-subscriber-hosts {
                        type yang:counter32;
                        description "The number of active subscriber hosts on this port and VLAN.";
                    }

                    container statistics {
                        description "Enter the statistics context";

                        leaf last-cleared-time {
                            type yang:date-and-time;
                            description "The time when the counters were last cleared.";
                        }

                        leaf ingress-packets {
                            type yang:counter64;
                            description "The number of IP packets received through this port and VLAN.";
                        }

                        leaf ingress-octets {
                            type yang:counter64;
                            description "The number of octets in IP packets received through this port and VLAN.";
                        }

                        leaf egress-packets {
                            type yang:counter64;
                            description "The number of IP packets sent through this port and VLAN.";
                        }

                        leaf egress-octets {
                            type yang:counter64;
                            description "The number of octets in IP packets sent through this port and VLAN.";
                        }

                    } // container statistics

                } // list svlan

            } // container subscriber-management

            container statistics {
                description "Enter the statistics context";

                leaf last-cleared-time {
                    type yang:date-and-time;
                    description
                        "Indicates the time, since system startup, when the counters in
                         IF-MIB::ifTable were last cleared.";
                }

                leaf in-discards {
                    type yang:counter64;
                    description
                        "Indicates the number of inbound packets which were chosen to be
                         discarded even though no errors had been detected to prevent
                         their being deliverable to a higher-layer protocol.  One
                         possible reason for discarding such a packet could be to
                         free up buffer space.

                         Discontinuities in the value of this counter can occur at
                         re-initialization of the management system, and at other
                         times as indicated by the value of
                         counter-discontinuity-time.";
                }

                leaf in-errors {
                    type yang:counter64;
                    description
                        "Indicates for packet-oriented interfaces, the number of inbound
                         packets that contained errors preventing them from being
                         deliverable to a higher-layer protocol.  For character-
                         oriented or fixed-length interfaces, the number of inbound
                         transmission units that contained errors preventing them
                         from being deliverable to a higher-layer protocol.

                         Discontinuities in the value of this counter can occur at
                         re-initialization of the management system, and at other
                         times as indicated by the value of
                         counter-discontinuity-time.";
                }

                leaf in-octets {
                    type yang:counter64;
                    description
                        "Indicates the total number of octets received on the interface,
                         including framing characters.

                         Discontinuities in the value of this counter can occur at
                         re-initialization of the management system, and at other
                         times as indicated by the value of
                         counter-discontinuity-time.";
                }

                leaf in-packets {
                    type yang:counter64;
                    description
                        "Indicates the total number of packets received on the interface,
                         including framing characters.

                         Discontinuities in the value of this counter can occur at
                         re-initialization of the management system, and at other
                         times as indicated by the value of
                         counter-discontinuity-time.";
                }

                leaf in-unknown-protocol-discards {
                    type yang:counter64;
                    description
                        "Indicates for packet-oriented interfaces, the number of packets
                         received via the interface which were discarded because of
                         an unknown or unsupported protocol.  For character-oriented
                         or fixed-length interfaces that support protocol
                         multiplexing the number of transmission units received via
                         the interface which were discarded because of an unknown or
                         unsupported protocol.  For any interface that does not
                         support protocol multiplexing, this counter will always be
                         0.

                         Discontinuities in the value of this counter can occur at
                         re-initialization of the management system, and at other
                         times as indicated by the value of
                         counter-discontinuity-time.";
                }

                leaf in-broadcast-packets {
                    type yang:counter64;
                    description
                        "Indicates the number of packets, delivered by this sub-layer to a
                         higher (sub-)layer, which were addressed to a broadcast
                         address at this sub-layer.

                         Discontinuities in the value of this counter can occur at
                         re-initialization of the management system, and at other
                         times as indicated by the value of
                         counter-discontinuity-time.";
                }

                leaf in-multicast-packets {
                    type yang:counter64;
                    description
                        "Indicates the number of packets, delivered by this sub-layer to a
                         higher (sub-)layer, which were addressed to a multicast
                         address at this sub-layer.  For a MAC layer protocol, this
                         includes both Group and Functional addresses.

                         Discontinuities in the value of this counter can occur at
                         re-initialization of the management system, and at other
                         times as indicated by the value of
                         counter-discontinuity-time.";
                }

                leaf in-unicast-packets {
                    type yang:counter64;
                    description
                        "Indicates the number of packets, delivered by this sub-layer to a
                         higher (sub-)layer, which were not addressed to a multicast
                         or broadcast address at this sub-layer.

                         Discontinuities in the value of this counter can occur at
                         re-initialization of the management system, and at other
                         times as indicated by the value of
                         counter-discontinuity-time.";
                }

                leaf out-discards {
                    type yang:counter64;
                    description
                        "Indicates the number of outbound packets which were chosen to be
                         discarded even though no errors had been detected to prevent
                         their being transmitted.  One possible reason for discarding
                         such a packet could be to free up buffer space.

                         Discontinuities in the value of this counter can occur at
                         re-initialization of the management system, and at other
                         times as indicated by the value of
                         counter-discontinuity-time.";
                }

                leaf out-errors {
                    type yang:counter64;
                    description
                        "Indicates for packet-oriented interfaces, the number of outbound
                         packets that could not be transmitted because of errors.
                         For character-oriented or fixed-length interfaces, the
                         number of outbound transmission units that could not be
                         transmitted because of errors.

                         Discontinuities in the value of this counter can occur at
                         re-initialization of the management system, and at other
                         times as indicated by the value of
                         counter-discontinuity-time.";
                }

                leaf out-octets {
                    type yang:counter64;
                    description
                        "Indicates the total number of octets transmitted out of the
                         interface, including framing characters.

                         Discontinuities in the value of this counter can occur at
                         re-initialization of the management system, and at other
                         times as indicated by the value of
                         counter-discontinuity-time.";
                }

                leaf out-packets {
                    type yang:counter64;
                    description
                        "Indicates the total number of packets transmitted out of the
                         interface, including framing characters.

                         Discontinuities in the value of this counter can occur at
                         re-initialization of the management system, and at other
                         times as indicated by the value of
                         counter-discontinuity-time.";
                }

                leaf out-broadcast-packets {
                    type yang:counter64;
                    description
                        "Indicates the total number of packets that higher-level protocols
                         requested be transmitted, and which were addressed to a
                         broadcast address at this sub-layer, including those that
                         were discarded or not sent.

                         Discontinuities in the value of this counter can occur at
                         re-initialization of the management system, and at other
                         times as indicated by the value of
                         counter-discontinuity-time.";
                }

                leaf out-multicast-packets {
                    type yang:counter64;
                    description
                        "Indicates the total number of packets that higher-level protocols
                         requested be transmitted, and which were addressed to a
                         multicast address at this sub-layer, including those that
                         were discarded or not sent.  For a MAC layer protocol, this
                         includes both Group and Functional addresses.

                         Discontinuities in the value of this counter can occur at
                         re-initialization of the management system, and at other
                         times as indicated by the value of
                         counter-discontinuity-time.";
                }

                leaf out-unicast-packets {
                    type yang:counter64;
                    description
                        "Indicates the total number of packets that higher-level protocols
                         requested be transmitted, and which were not addressed to a
                         multicast or broadcast address at this sub-layer, including
                         those that were discarded or not sent.

                         Discontinuities in the value of this counter can occur at
                         re-initialization of the management system, and at other
                         times as indicated by the value of
                         counter-discontinuity-time.";
                }

                container aggregate-queue {
                    description "Enter the aggregate-queue context";

                    leaf ingress-forward-packets {
                        type yang:counter64;
                        description
                            "Indicates the total number of ingress packets forwarded by all queues on
                             the member ports.";
                    }

                    leaf ingress-forward-octets {
                        type yang:counter64;
                        description
                            "Indicates the total number of ingress octets forwarded by all queues on
                             the member ports.";
                    }

                    leaf egress-forward-packets {
                        type yang:counter64;
                        description
                            "Indicates the total number of egress packets forwarded by all queues on
                             the member ports.";
                    }

                    leaf egress-forward-octets {
                        type yang:counter64;
                        description
                            "Indicates the total number of egress octets forwarded by all queues on
                             the member ports.";
                    }

                    leaf ingress-drop-packets {
                        type yang:counter64;
                        description
                            "Indicates the total number of dropped ingress packets by all queues on
                             the member ports.";
                    }

                    leaf ingress-drop-octets {
                        type yang:counter64;
                        description
                            "Indicates the total number of dropped ingress octets by all queues on
                             the member ports.";
                    }

                    leaf egress-drop-packets {
                        type yang:counter64;
                        description
                            "Indicates the total number of dropped egress packets by all queues on
                             the member ports.";
                    }

                    leaf egress-drop-octets {
                        type yang:counter64;
                        description
                            "Indicates the total number of dropped egress octets by all queues on
                             the member ports.";
                    }

                } // container aggregate-queue

            } // container statistics

            container port-scheduler-policy {
                description "Enter the port-scheduler-policy context";

                container statistics {
                    description "Enter the statistics context";

                    leaf policy-name {
                        type types-sros:named-item-or-empty;
                        description "Specifies an port scheduler policy.";
                    }

                    leaf total-forwarded-octets {
                        type yang:counter64;
                        description "Indicates the total number of octets forwarded.";
                    }

                    leaf total-forwarded-packets {
                        type yang:counter64;
                        description "Indicates the total number of packets forwarded.";
                    }

                    leaf total-dropped-octets {
                        type yang:counter64;
                        description "Indicates the total number of octets dropped.";
                    }

                    leaf total-dropped-packets {
                        type yang:counter64;
                        description "Indicates the total number of packets dropped.";
                    }

                    list level {
                        key "priority-level";
                        description "Enter the level list instance";

                        leaf priority-level {
                            type uint32 {
                                range "1..8";
                            }
                            description "Specifies the priority level of the port scheduler policy.";
                        }

                        leaf forwarded-octets {
                            type yang:counter64;
                            description "Indicates the number of octets forwarded for this level.";
                        }

                        leaf forwarded-packets {
                            type yang:counter64;
                            description "Indicates the number of packets forwarded for this level.";
                        }

                        leaf dropped-octets {
                            type yang:counter64;
                            description "Indicates the number of octets dropped for this level.";
                        }

                        leaf dropped-packets {
                            type yang:counter64;
                            description "Indicates the number of packets dropped for this level.";
                        }

                    } // list level

                } // container statistics

            } // container port-scheduler-policy

            container lldp-member-template {
                description "Enter the lldp-member-template context";

                list dest-mac {
                    key "mac-type";
                    description "Enter the dest-mac list instance";

                    leaf mac-type {
                        type types-lldp:mac-addr-type;
                        description "The identifier which uniquely identifies the MAC address type.";
                    }

                    list tx-mgmt-address {
                        key "mgmt-address-system-type";
                        description "Enter the tx-mgmt-address list instance";

                        leaf mgmt-address-system-type {
                            type enumeration {
                                enum oob                            { value 0; }
                                enum system                         { value 1; }
                                enum system-ipv6                    { value 2; }
                                enum oob-ipv6                       { value 3; }
                            }
                            description "The identifier which uniquely identifies the management address.";
                        }

                        leaf mgmt-address {
                            type types-sros:ip-address;
                            description "Indicates the management address.";
                        }

                    } // list tx-mgmt-address

                } // list dest-mac

            } // container lldp-member-template

        } // list lag

    } // grouping state-lag

}
