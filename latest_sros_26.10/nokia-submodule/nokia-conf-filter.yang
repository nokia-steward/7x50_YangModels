submodule nokia-conf-filter {

    yang-version "1.1";

    belongs-to nokia-conf { prefix "conf"; }

    import ietf-yang-types                { prefix "yang"; }
    import nokia-sros-yang-extensions     { prefix "sros-ext"; }
    import nokia-types-filter             { prefix "types-filter"; }
    import nokia-types-qos                { prefix "types-qos"; }
    import nokia-types-services           { prefix "types-services"; }
    import nokia-types-sros               { prefix "types-sros"; }
    import nokia-types-subscriber-mgmt    { prefix "types-submgt"; }

    include nokia-conf-cflowd;
    include nokia-conf-filter-dhcp;
    include nokia-conf-filter-ip-exception;
    include nokia-conf-groups;
    include nokia-conf-log;
    include nokia-conf-router;
    include nokia-conf-router-mpls;
    include nokia-conf-service;
    include nokia-conf-svc-nat;
    include nokia-conf-svc-vpls;
    include nokia-conf-svc-vprn;

    sros-ext:sros-major-release "rel26";
    organization "Nokia";
    contact
        "Nokia SR OS Support
         Web: <http://www.nokia.com>";
    description
        "Nokia YANG Data model to configure line card ACL filters on SR OS based routers.

         Copyright 2016 Nokia. All rights reserved. Reproduction of this document
         is authorized on the condition that the foregoing copyright notice is included.

         This nokia-conf-filter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping conf-filter {
        container filter {
            description "Enter the filter context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list redirect-policy {
                key "redirect-policy-name";
                description "Enter the redirect-policy list instance";

                leaf redirect-policy-name {
                    type types-sros:named-item;
                    description "Redirect policy name";
                }

                leaf admin-state {
                    type types-sros:admin-state;
                    default "disable";
                    description "Administrative state of the redirect policy";
                }

                leaf description {
                    type types-sros:description;
                    description "Text description";
                }

                leaf router-instance {
                    type string;
                    description "Routing context to use for route lookup";
                }

                leaf sticky-dest {
                    type types-filter:filter-sticky-dest;
                    units "seconds";
                    description "Time required by system before applying the current best destination as active destination";
                }

                leaf notify-dest-change {
                    type boolean;
                    default "false";
                    description "Send notifications when the active destination changes";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list destination {
                    key "destination-address";
                    description "Enter the destination list instance";

                    leaf destination-address {
                        type types-sros:ip-unicast-address;
                        description "IP address and type of destination";
                    }

                    leaf admin-state {
                        type types-sros:admin-state;
                        default "disable";
                        description "Administrative state of the destination";
                    }

                    leaf description {
                        type types-sros:description;
                        description "Text description";
                    }

                    leaf priority {
                        type uint32 {
                            range "1..255";
                        }
                        default "100";
                        description "Priority for this destination";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container ping-test {
                        presence "Enable the ping-test context";
                        description "Enable the ping-test context";

                        leaf source-address {
                            type types-sros:ip-address;
                            description "Source address to use in the IP packet of the ping test";
                        }

                        leaf interval {
                            type uint32 {
                                range "1..60";
                            }
                            units "seconds";
                            default "1";
                            description "Time between consecutive requests which are sent to the far end host";
                        }

                        leaf timeout {
                            type uint32 {
                                range "1..60";
                            }
                            units "seconds";
                            default "1";
                            description "Time required to receive a response from the far end host";
                        }

                        leaf drop-count {
                            type uint32 {
                                range "1..60";
                            }
                            default "3";
                            description "Number of consecutive requests that fail before destination is declared unreachable";
                        }

                        leaf hold-down {
                            type uint32 {
                                range "0..86400";
                            }
                            units "seconds";
                            default "0";
                            description "Time for the system to be held down if this test has marked it unreachable";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container ping-test

                    container unicast-rt-test {
                        presence "Enable the unicast-rt-test context";
                        description "Enable the unicast-rt-test context";

                    } // container unicast-rt-test

                } // list destination

            } // list redirect-policy

            list redirect-policy-binding {
                key "binding-name";
                max-elements 16;
                description "Enter the redirect-policy-binding list instance";

                leaf binding-name {
                    type types-sros:named-item;
                    description "Binding name";
                }

                leaf binding-operator {
                    type types-filter:filter-binding-operator;
                    default "and";
                    description "Logical operator used to obtain the master test result";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list redirect-policy {
                    key "redirect-policy-name";
                    description "Enter the redirect-policy list instance";

                    leaf redirect-policy-name {
                        type leafref {
                            path "../../../redirect-policy/redirect-policy-name";
                        }
                        description "Redirect policy name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list destination {
                        key "destination-address";
                        min-elements 1;
                        description "Add a list entry for destination";

                        leaf destination-address {
                            type leafref {
                                path "../../../../redirect-policy[redirect-policy-name=current()/../../redirect-policy-name]/destination/destination-address";
                            }
                            description "IP address of redirect policy destination to binding";
                        }

                    } // list destination

                } // list redirect-policy

            } // list redirect-policy-binding

            list log {
                key "log-id";
                description "Enter the log list instance";

                leaf log-id {
                    type types-filter:filter-log-id;
                    description "Filter log identifier";
                }

                leaf description {
                    type types-sros:description-or-empty;
                    description "Text description";
                }

                leaf admin-state {
                    type types-sros:admin-state;
                    default "enable";
                    description "Administrative state of filter logging";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container destination {
                    description "Enter the destination context";

                    choice destination {
                        default "memory";
                        case memory {

                            container memory {
                                description "Enter the memory context";

                                leaf max-entries {
                                    type uint32 {
                                        range "1..50000";
                                    }
                                    default "1000";
                                    description "Maximum number of memory entries that the log can store";
                                }

                                leaf stop-on-full {
                                    type boolean;
                                    default "false";
                                    description "Stop logging when maximum number of memory entries is reached or wrap-around is used";
                                }

                            } // container memory

                        }
                        case syslog {

                            container syslog {
                                description "Enter the syslog context";

                                leaf syslog-id {
                                    status obsolete;
                                    type leafref {
                                        path "../../../../../log/syslog/syslog-name";
                                    }
                                    description "ID of the Syslog server definition for filter logs";
                                }

                                leaf name {
                                    type leafref {
                                        path "../../../../../log/syslog/syslog-name";
                                    }
                                    description "Syslog server definition ID";
                                }

                                container summary {
                                    description "Enter the summary context";

                                    leaf admin-state {
                                        type types-sros:admin-state;
                                        default "disable";
                                        description "Administrative state of filter log summarization";
                                    }

                                    leaf summary-crit {
                                        type types-filter:filter-log-summary-criterion;
                                        default "src-addr";
                                        description "Summary for filter log entries";
                                    }

                                } // container summary

                            } // container syslog

                        }
                    }
                } // container destination

            } // list log

            container match-list {
                description "Enter the match-list context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list protocol-list {
                    key "protocol-list-name";
                    max-elements 512;
                    description "Enter the protocol-list list instance";

                    leaf protocol-list-name {
                        type types-sros:named-item;
                        description "Protocol list name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list protocol {
                        key "protocol-id";
                        max-elements 32;
                        description "Add a list entry for protocol";

                        leaf protocol-id {
                            type types-sros:ip-protocol;
                            description "IP protocol identifier";
                        }

                    } // list protocol

                } // list protocol-list

                list ip-prefix-list {
                    key "prefix-list-name";
                    description "Enter the ip-prefix-list list instance";

                    leaf prefix-list-name {
                        type types-sros:named-item;
                        description "IP prefix list name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container apply-path {
                        description "Enter the apply-path context";

                        list bgp-peers {
                            key "criterion-index";
                            description "Enter the bgp-peers list instance";

                            leaf criterion-index {
                                type uint32 {
                                    range "1..255";
                                }
                                description "Index defining BGP peers for prefix autogeneration";
                            }

                            leaf group {
                                type types-sros:regular-expression-not-all-spaces;
                                sros-ext:immutable;
                                mandatory true;
                                description "Regular expression to match against the base router BGP instance group configuration";
                            }

                            leaf neighbor {
                                type types-sros:regular-expression-not-all-spaces;
                                sros-ext:immutable;
                                mandatory true;
                                description "Regular expression to match against the base router BGP instance neighbor configuration";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice router-match {
                                default "router-instance";
                                case router-instance {

                                    leaf router-instance {
                                        type string;
                                        sros-ext:immutable;
                                        default "Base";
                                        description "Router name or VPRN service name";
                                    }

                                }
                                case service-name-match {

                                    leaf service-name-match {
                                        type types-sros:regular-expression-not-all-spaces;
                                        sros-ext:immutable;
                                        description "Regular expression to match against VPRN service name";
                                    }

                                }
                            }
                        } // list bgp-peers

                        list interfaces {
                            key "criterion-index";
                            description "Enter the interfaces list instance";

                            leaf criterion-index {
                                type uint32 {
                                    range "1..255";
                                }
                                description "Index defining interfaces for prefix autogeneration";
                            }

                            leaf interface {
                                type types-sros:regular-expression-not-all-spaces;
                                sros-ext:immutable;
                                mandatory true;
                                description "Regular expression defining a match string";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice router-match {
                                default "router-instance";
                                case router-instance {

                                    leaf router-instance {
                                        type string;
                                        sros-ext:immutable;
                                        default "Base";
                                        description "Router name or VPRN service name";
                                    }

                                }
                                case service-name-match {

                                    leaf service-name-match {
                                        type types-sros:regular-expression-not-all-spaces;
                                        sros-ext:immutable;
                                        description "Regular expression to match against VPRN service name";
                                    }

                                }
                            }
                        } // list interfaces



                    } // container apply-path

                    list prefix {
                        key "ip-prefix";
                        max-elements 8192;
                        description "Add a list entry for prefix";

                        leaf ip-prefix {
                            type types-sros:ipv4-prefix;
                            description "IPv4 prefix to be added to the prefix list";
                        }

                    } // list prefix

                    list prefix-exclude {
                        key "ip-prefix";
                        max-elements 512;
                        description "Add a list entry for prefix-exclude";

                        leaf ip-prefix {
                            type types-sros:ipv4-prefix;
                            description "IPv4 prefix to be added to the prefix list";
                        }

                    } // list prefix-exclude

                } // list ip-prefix-list

                list ipv6-prefix-list {
                    key "prefix-list-name";
                    description "Enter the ipv6-prefix-list list instance";

                    leaf prefix-list-name {
                        type types-sros:named-item;
                        description "IP prefix list name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container apply-path {
                        description "Enter the apply-path context";

                        list bgp-peers {
                            key "criterion-index";
                            description "Enter the bgp-peers list instance";

                            leaf criterion-index {
                                type uint32 {
                                    range "1..255";
                                }
                                description "Index defining BGP peers for prefix autogeneration";
                            }

                            leaf group {
                                type types-sros:regular-expression-not-all-spaces;
                                sros-ext:immutable;
                                mandatory true;
                                description "Regular expression to match against the base router BGP instance group configuration";
                            }

                            leaf neighbor {
                                type types-sros:regular-expression-not-all-spaces;
                                sros-ext:immutable;
                                mandatory true;
                                description "Regular expression to match against the base router BGP instance neighbor configuration";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice router-match {
                                default "router-instance";
                                case router-instance {

                                    leaf router-instance {
                                        type string;
                                        sros-ext:immutable;
                                        default "Base";
                                        description "Router name or VPRN service name";
                                    }

                                }
                                case service-name-match {

                                    leaf service-name-match {
                                        type types-sros:regular-expression-not-all-spaces;
                                        sros-ext:immutable;
                                        description "Regular expression to match against VPRN service name";
                                    }

                                }
                            }
                        } // list bgp-peers

                        list interfaces {
                            key "criterion-index";
                            description "Enter the interfaces list instance";

                            leaf criterion-index {
                                type uint32 {
                                    range "1..255";
                                }
                                description "Index defining interfaces for prefix autogeneration";
                            }

                            leaf interface {
                                type types-sros:regular-expression-not-all-spaces;
                                sros-ext:immutable;
                                mandatory true;
                                description "Regular expression defining a match string";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice router-match {
                                default "router-instance";
                                case router-instance {

                                    leaf router-instance {
                                        type string;
                                        sros-ext:immutable;
                                        default "Base";
                                        description "Router name or VPRN service name";
                                    }

                                }
                                case service-name-match {

                                    leaf service-name-match {
                                        type types-sros:regular-expression-not-all-spaces;
                                        sros-ext:immutable;
                                        description "Regular expression to match against VPRN service name";
                                    }

                                }
                            }
                        } // list interfaces


                    } // container apply-path

                    list prefix {
                        key "ipv6-prefix";
                        max-elements 8192;
                        description "Add a list entry for prefix";

                        leaf ipv6-prefix {
                            type types-sros:ipv6-prefix;
                            description "IPv6 prefix to be added to the prefix list";
                        }

                    } // list prefix

                    list prefix-exclude {
                        key "ipv6-prefix";
                        max-elements 512;
                        description "Add a list entry for prefix-exclude";

                        leaf ipv6-prefix {
                            type types-sros:ipv6-prefix;
                            description "IPv6 prefix to be added to the prefix list";
                        }

                    } // list prefix-exclude

                } // list ipv6-prefix-list

                list port-list {
                    key "port-list-name";
                    max-elements 5120;
                    description "Enter the port-list list instance";

                    leaf port-list-name {
                        type types-sros:named-item;
                        description "Port list name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list port {
                        key "value";
                        description "Add a list entry for port";

                        leaf value {
                            type int32 {
                                range "0..65535";
                            }
                            description "Port value";
                        }

                    } // list port

                    list range {
                        key "start end";
                        description "Add a list entry for range";

                        leaf start {
                            type int32 {
                                range "0..65534";
                            }
                            description "Lower bound of the port list range";
                        }

                        leaf end {
                            type int32 {
                                range "1..65535";
                            }
                            description "Upper bound of the port list range";
                        }

                    } // list range

                } // list port-list

                list ip-packet-length-list {
                    key "packet-length-list-name";
                    description "Enter the ip-packet-length-list list instance";

                    leaf packet-length-list-name {
                        type types-sros:named-item;
                        description "Name of the packet length list";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list packet-length {
                        key "value";
                        description "Add a list entry for packet-length";

                        leaf value {
                            type int32 {
                                range "0..65535";
                            }
                            description "Packet length";
                        }

                    } // list packet-length

                    list range {
                        key "start end";
                        description "Add a list entry for range";

                        leaf start {
                            type int32 {
                                range "0..65534";
                            }
                            description "Lower bound of the packet length range";
                        }

                        leaf end {
                            type int32 {
                                range "1..65535";
                            }
                            description "Upper bound of the packet length range";
                        }

                    } // list range

                } // list ip-packet-length-list

                list ipv6-packet-length-list {
                    key "packet-length-list-name";
                    description "Enter the ipv6-packet-length-list list instance";

                    leaf packet-length-list-name {
                        type types-sros:named-item;
                        description "Name of the packet length list";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list packet-length {
                        key "value";
                        description "Add a list entry for packet-length";

                        leaf value {
                            type int32 {
                                range "40..65575";
                            }
                            description "Packet length";
                        }

                    } // list packet-length

                    list range {
                        key "start end";
                        description "Add a list entry for range";

                        leaf start {
                            type int32 {
                                range "40..65574";
                            }
                            description "Lower bound of the packet length range";
                        }

                        leaf end {
                            type int32 {
                                range "41..65575";
                            }
                            description "Upper bound of the packet length range";
                        }

                    } // list range

                } // list ipv6-packet-length-list

            } // container match-list

            list ip-filter {
                key "filter-name";
                description "Enter the ip-filter list instance";

                leaf filter-name {
                    type types-filter:filter-name;
                    description "Filter name";
                }

                leaf default-action {
                    type types-filter:filter-default-action;
                    default "drop";
                    description "Action for packets that do not match any entry";
                }

                leaf description {
                    type types-sros:description;
                    description "Text description";
                }

                leaf scope {
                    type types-filter:filter-scope;
                    default "template";
                    description "Scope of the filter definition";
                }

                leaf type {
                    type enumeration {
                        enum normal                         { value 0; }
                        enum src-mac                        { value 1; }
                        enum packet-length                  { value 2; }
                        enum destination-class              { value 3; }
                    }
                    default "normal";
                    description "Set of match criteria for the filter policy";
                }

                leaf chain-to-system-filter {
                    type boolean;
                    default "false";
                    description "Chain filter policy to the active IPvX system filter policy";
                }

                leaf shared-policer {
                    type boolean;
                    default "false";
                    description "Share policer among active ports in the LAG";
                }

                leaf filter-id {
                    type types-filter:filter-id;
                    sros-ext:immutable;
                    description "IP filter ID";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container subscriber-mgmt {
                    description "Enter the subscriber-mgmt context";

                    container host-specific-entry {
                        description "Enter the host-specific-entry context";

                        container filter-rule {
                            description "Enter the filter-rule context";

                            container range {
                                presence "Enable the range context";
                                description "Enable the range context";

                                leaf start {
                                    type types-filter:entry-id;
                                    mandatory true;
                                    description "Lower bound of range for inserting filter rule entries";
                                }

                                leaf end {
                                    type types-filter:entry-id;
                                    mandatory true;
                                    description "Upper bound of range for inserting filter rule entries";
                                }

                            } // container range

                        } // container filter-rule

                        container credit-control {
                            description "Enter the credit-control context";

                            container range {
                                presence "Enable the range context";
                                description "Enable the range context";

                                leaf start {
                                    type types-filter:entry-id;
                                    mandatory true;
                                    description "Lower bound of range for credit control filter entries";
                                }

                                leaf end {
                                    type types-filter:entry-id;
                                    mandatory true;
                                    description "Upper bound of range for credit control filter entries";
                                }

                            } // container range

                        } // container credit-control

                        container watermark {
                            description "Enter the watermark context";

                            leaf low {
                                type int32 {
                                    range "0..100";
                                }
                                default "90";
                                description "Low watermark for host-specific entries, to clear a table full alarm";
                            }

                            leaf high {
                                type int32 {
                                    range "0..100";
                                }
                                default "95";
                                description "High watermark for host-specific entries, to raise a table full alarm";
                            }

                        } // container watermark

                    } // container host-specific-entry

                    container shared-entry {
                        description "Enter the shared-entry context";

                        container filter-rule {
                            description "Enter the filter-rule context";

                            container range {
                                presence "Enable the range context";
                                description "Enable the range context";

                                leaf start {
                                    type types-filter:entry-id;
                                    mandatory true;
                                    description "Lower bound of range for inserting shared host rules";
                                }

                                leaf end {
                                    type types-filter:entry-id;
                                    mandatory true;
                                    description "Upper bound of range for inserting shared host rules";
                                }

                            } // container range

                        } // container filter-rule

                        container pcc-rule {
                            description "Enter the pcc-rule context";

                            container range {
                                presence "Enable the range context";
                                description "Enable the range context";

                                leaf start {
                                    type types-filter:entry-id;
                                    mandatory true;
                                    description "Lower bound of the range for PCC rule filter entries";
                                }

                                leaf end {
                                    type types-filter:entry-id;
                                    mandatory true;
                                    description "Upper bound of the range for PCC rule filter entries";
                                }

                            } // container range

                        } // container pcc-rule

                        container watermark {
                            presence "Enable the watermark context";
                            description "Enable the watermark context";

                            leaf low {
                                type int32 {
                                    range "0..7999";
                                }
                                mandatory true;
                                description "Limit of RADIUS or Diameter shared filters before clearing high watermark notification";
                            }

                            leaf high {
                                type int32 {
                                    range "1..8000";
                                }
                                mandatory true;
                                description "Limit of RADIUS shared filters before generating high watermark notification";
                            }

                        } // container watermark

                    } // container shared-entry

                } // container subscriber-mgmt

                list entry {
                    key "entry-id";
                    description "Enter the entry list instance";

                    leaf entry-id {
                        type types-filter:entry-id;
                        description "ID for a match criteria and the corresponding action";
                    }

                    leaf description {
                        type types-sros:description;
                        description "Text description";
                    }

                    leaf pbr-down-action-override {
                        type types-filter:filter-pbr-down-action-ovr;
                        description "Action when PBR or PBF target for this entry is not available";
                    }

                    leaf sticky-dest {
                        type types-filter:filter-sticky-dest;
                        units "seconds";
                        description "Time before action with available PBR or PBF destination and highest priority";
                    }

                    leaf log {
                        type leafref {
                            path "../../../log/log-id";
                        }
                        description "Log that is used for packets matching this entry";
                    }

                    leaf collect-stats {
                        type boolean;
                        default "false";
                        description "Enable statistics collection for an entry";
                    }

                    leaf egress-pbr {
                        type types-filter:filter-egress-pbr;
                        sros-ext:immutable;
                        description "PBR that has an effect when this filter is applied on egress";
                    }

                    leaf filter-sample {
                        type boolean;
                        default "false";
                        description "Sample matching traffic if IP interface is set to cflowd ACL mode";
                    }

                    leaf interface-sample {
                        type boolean;
                        default "true";
                        description "Sample matching traffic if IP interface is set to cflowd interface mode";
                    }

                    leaf sample-profile {
                        type leafref {
                            path "../../../../cflowd/sample-profile/profile-id";
                        }
                        description "Cflowd sample profile ID to match packets";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container match {
                        description "Enter the match context";

                        leaf dscp {
                            type types-qos:dscp-name;
                            description "DSCP used as an IP filter match criterion";
                        }

                        leaf fragment {
                            type enumeration {
                                enum false                          { value 2; }
                                enum true                           { value 3; }
                                enum first-only                     { value 4; }
                                enum non-first-only                 { value 5; }
                            }
                            description "Match criterion for fragmented packets";
                        }

                        leaf multiple-option {
                            type boolean;
                            description "Match based on presence of multiple options in header";
                        }

                        leaf option-present {
                            type boolean;
                            description "Match on any IP option present in the packet";
                        }

                        leaf src-route-option {
                            type boolean;
                            description "Match based on presence of source route option";
                        }

                        leaf destination-class {
                            type types-sros:class-index;
                            description "Destination class as a match criterion";
                        }

                        choice match-protocol-choice {
                            case protocol {

                                leaf protocol {
                                    type types-sros:match-ip-protocol;
                                    description "IP protocol identifier as a match criterion";
                                }

                            }
                            case protocol-list {

                                leaf-list protocol-list {
                                    type leafref {
                                        path "../../../../match-list/protocol-list/protocol-list-name";
                                    }
                                    max-elements 16;
                                    description "Name of the protocol list as a match criterion";
                                }

                            }
                        }
                        choice ip-selector {
                            case src-dst-ip {

                                container src-ip {
                                    description "Enter the src-ip context";

                                    choice match-address-choice {
                                        case address-and-prefix-or-mask {

                                            leaf address {
                                                type union {
                                                    type types-sros:ipv4-prefix-with-host-bits;
                                                    type types-sros:ipv4-address;
                                                }
                                                description "IPv4 address used as the match criterion";
                                            }

                                            leaf mask {
                                                type types-sros:ipv4-address;
                                                description "IPv4 address mask used as the match criterion";
                                            }

                                        }
                                        case ip-prefix-list {

                                            leaf-list ip-prefix-list {
                                                type leafref {
                                                    path "../../../../../match-list/ip-prefix-list/prefix-list-name";
                                                }
                                                max-elements 16;
                                                description "IPv4 address prefix list used as match criterion";
                                            }

                                        }
                                    }
                                } // container src-ip

                                container dst-ip {
                                    description "Enter the dst-ip context";

                                    choice match-address-choice {
                                        case address-and-prefix-or-mask {

                                            leaf address {
                                                type union {
                                                    type types-sros:ipv4-prefix-with-host-bits;
                                                    type types-sros:ipv4-address;
                                                }
                                                description "IPv4 address used as the match criterion";
                                            }

                                            leaf mask {
                                                type types-sros:ipv4-address;
                                                description "IPv4 address mask used as the match criterion";
                                            }

                                        }
                                        case ip-prefix-list {

                                            leaf-list ip-prefix-list {
                                                type leafref {
                                                    path "../../../../../match-list/ip-prefix-list/prefix-list-name";
                                                }
                                                max-elements 16;
                                                description "IPv4 address prefix list used as match criterion";
                                            }

                                        }
                                    }
                                } // container dst-ip

                            }
                            case ip {

                                container ip {
                                    description "Enter the ip context";

                                    choice match-address-choice {
                                        case address-and-prefix-or-mask {

                                            leaf address {
                                                type union {
                                                    type types-sros:ipv4-prefix-with-host-bits;
                                                    type types-sros:ipv4-address;
                                                }
                                                description "IPv4 address used as the match criterion";
                                            }

                                            leaf mask {
                                                type types-sros:ipv4-address;
                                                description "IPv4 address mask used as the match criterion";
                                            }

                                        }
                                        case ip-prefix-list {

                                            leaf-list ip-prefix-list {
                                                type leafref {
                                                    path "../../../../../match-list/ip-prefix-list/prefix-list-name";
                                                }
                                                max-elements 16;
                                                description "IPv4 address prefix list used as match criterion";
                                            }

                                        }
                                    }
                                } // container ip

                            }
                        }
                        choice port-selector {
                            case src-dst-port {

                                container src-port {
                                    description "Enter the src-port context";

                                    choice port {
                                        case eq {

                                            leaf eq {
                                                type uint16 {
                                                    range "0..65535";
                                                }
                                                description "Exact value as the match criterion";
                                            }

                                        }
                                        case lt {

                                            leaf lt {
                                                type uint16 {
                                                    range "1..65535";
                                                }
                                                description "Less than value as the match criterion";
                                            }

                                        }
                                        case gt {

                                            leaf gt {
                                                type uint16 {
                                                    range "0..65534";
                                                }
                                                description "Greater than value as the match criterion";
                                            }

                                        }
                                        case range {

                                            container range {
                                                presence "Enable the range context";
                                                description "Enable the range context";

                                                leaf start {
                                                    type uint16 {
                                                        range "0..65534";
                                                    }
                                                    mandatory true;
                                                    description "Lower bound of the port range";
                                                }

                                                leaf end {
                                                    type uint16 {
                                                        range "1..65535";
                                                    }
                                                    mandatory true;
                                                    description "Upper bound of the port range";
                                                }

                                            } // container range

                                        }
                                        case port-list {

                                            leaf-list port-list {
                                                type leafref {
                                                    path "../../../../../match-list/port-list/port-list-name";
                                                }
                                                max-elements 16;
                                                description "Name of the port list as the match criterion";
                                            }

                                        }
                                    }
                                } // container src-port

                                container dst-port {
                                    description "Enter the dst-port context";

                                    choice port {
                                        case eq {

                                            leaf eq {
                                                type uint16 {
                                                    range "0..65535";
                                                }
                                                description "Exact value as the match criterion";
                                            }

                                        }
                                        case lt {

                                            leaf lt {
                                                type uint16 {
                                                    range "1..65535";
                                                }
                                                description "Less than value as the match criterion";
                                            }

                                        }
                                        case gt {

                                            leaf gt {
                                                type uint16 {
                                                    range "0..65534";
                                                }
                                                description "Greater than value as the match criterion";
                                            }

                                        }
                                        case range {

                                            container range {
                                                presence "Enable the range context";
                                                description "Enable the range context";

                                                leaf start {
                                                    type uint16 {
                                                        range "0..65534";
                                                    }
                                                    mandatory true;
                                                    description "Lower bound of the port range";
                                                }

                                                leaf end {
                                                    type uint16 {
                                                        range "1..65535";
                                                    }
                                                    mandatory true;
                                                    description "Upper bound of the port range";
                                                }

                                            } // container range

                                        }
                                        case port-list {

                                            leaf-list port-list {
                                                type leafref {
                                                    path "../../../../../match-list/port-list/port-list-name";
                                                }
                                                max-elements 16;
                                                description "Name of the port list as the match criterion";
                                            }

                                        }
                                    }
                                } // container dst-port

                            }
                            case port {

                                container port {
                                    description "Enter the port context";

                                    choice port {
                                        case eq {

                                            leaf eq {
                                                type uint16 {
                                                    range "0..65535";
                                                }
                                                description "Exact value as the match criterion";
                                            }

                                        }
                                        case lt {

                                            leaf lt {
                                                type uint16 {
                                                    range "1..65535";
                                                }
                                                description "Less than value as the match criterion";
                                            }

                                        }
                                        case gt {

                                            leaf gt {
                                                type uint16 {
                                                    range "0..65534";
                                                }
                                                description "Greater than value as the match criterion";
                                            }

                                        }
                                        case range {

                                            container range {
                                                presence "Enable the range context";
                                                description "Enable the range context";

                                                leaf start {
                                                    type uint16 {
                                                        range "0..65534";
                                                    }
                                                    mandatory true;
                                                    description "Lower bound of the port range";
                                                }

                                                leaf end {
                                                    type uint16 {
                                                        range "1..65535";
                                                    }
                                                    mandatory true;
                                                    description "Upper bound of the port range";
                                                }

                                            } // container range

                                        }
                                        case port-list {

                                            leaf-list port-list {
                                                type leafref {
                                                    path "../../../../../match-list/port-list/port-list-name";
                                                }
                                                max-elements 16;
                                                description "Name of the port list as the match criterion";
                                            }

                                        }
                                    }
                                } // container port

                            }
                        }
                        choice match-tcp-flags {
                            case tcp-established {

                                leaf tcp-established {
                                    type empty;
                                    description "Use ACK or RST status in TCP header as match criterion";
                                }

                            }
                            case tcp-flags {

                                container tcp-flags {
                                    description "Enter the tcp-flags context";

                                    leaf ack {
                                        type boolean;
                                        description "Use ACK TCP bit status in TCP header as match criterion";
                                    }

                                    leaf syn {
                                        type boolean;
                                        description "Use SYN TCP bit status in TCP header as match criterion";
                                    }

                                    leaf fin {
                                        type boolean;
                                        description "Use FIN TCP bit status in TCP header as match criterion";
                                    }

                                    leaf rst {
                                        type boolean;
                                        description "Use RST TCP bit status in TCP header as match criterion";
                                    }

                                    leaf psh {
                                        type boolean;
                                        description "Use PSH TCP bit status in TCP header as match criterion";
                                    }

                                    leaf urg {
                                        type boolean;
                                        description "Use URG TCP bit status in TCP header as match criterion";
                                    }

                                    leaf ece {
                                        type boolean;
                                        description "Use ECE TCP bit status in TCP header as match criterion";
                                    }

                                    leaf cwr {
                                        type boolean;
                                        description "Use CWR TCP bit status in TCP header as match criterion";
                                    }

                                    leaf ns {
                                        type boolean;
                                        description "Use NS TCP bit status in TCP header as match criterion";
                                    }

                                } // container tcp-flags

                            }
                        }
                        container ip-option {
                            presence "Enable the ip-option context";
                            description "Enable the ip-option context";

                            leaf type {
                                type types-filter:filter-match-ip-option;
                                mandatory true;
                                description "IP option to match";
                            }

                            leaf mask {
                                type types-filter:filter-match-ip-option {
                                    range "1..255";
                                }
                                default "255";
                                description "Mask used with the IP option value in the packet header";
                            }

                        } // container ip-option

                        container src-mac {
                            presence "Enable the src-mac context";
                            description "Enable the src-mac context";

                            leaf address {
                                type yang:mac-address;
                                mandatory true;
                                description "MAC address used as the match criterion";
                            }

                            leaf mask {
                                type yang:mac-address;
                                default "ff:ff:ff:ff:ff:ff";
                                description "MAC address mask as the match criterion";
                            }

                        } // container src-mac

                        container icmp {
                            description "Enter the icmp context";

                            choice icmp-code {
                                case code {

                                    leaf code {
                                        type types-filter:ipv4-match-icmp-codes;
                                        description "ICMP code value to match";
                                    }

                                }
                            }
                            choice icmp-type {
                                case type {

                                    leaf type {
                                        type types-filter:ipv4-match-icmp-types;
                                        description "ICMP type value to match";
                                    }

                                }
                            }
                        } // container icmp

                        container packet-length {
                            presence "Enable the packet-length context";
                            description "Enable the packet-length context";

                            choice packet-length {
                                mandatory true;
                                case eq {

                                    leaf eq {
                                        type types-filter:pkt-len-or-payload-len-value;
                                        description "Exact match criterion for the length";
                                    }

                                }
                                case lt {

                                    leaf lt {
                                        type types-filter:pkt-len-or-payload-len-lt-value;
                                        description "Less than match criterion for the length";
                                    }

                                }
                                case gt {

                                    leaf gt {
                                        type types-filter:pkt-len-or-payload-len-gt-value;
                                        description "Greater than match criterion for the length";
                                    }

                                }
                                case range {

                                    container range {
                                        presence "Enable the range context";
                                        description "Enable the range context";

                                        leaf start {
                                            type types-filter:pkt-len-or-payload-len-gt-value;
                                            mandatory true;
                                            description "Lower bound of the length range";
                                        }

                                        leaf end {
                                            type types-filter:pkt-len-or-payload-len-lt-value;
                                            mandatory true;
                                            description "Upper bound of the length range";
                                        }

                                    } // container range

                                }
                                case ip-packet-length-list {

                                    leaf-list ip-packet-length-list {
                                        type leafref {
                                            path "../../../../../match-list/ip-packet-length-list/packet-length-list-name";
                                        }
                                        max-elements 16;
                                        description "Packet length list to match";
                                    }

                                }
                            }
                        } // container packet-length

                        container ttl {
                            presence "Enable the ttl context";
                            description "Enable the ttl context";

                            choice ttl {
                                mandatory true;
                                case eq {

                                    leaf eq {
                                        type types-filter:ttl-or-hop-limit-value;
                                        description "Equal to condition match value";
                                    }

                                }
                                case lt {

                                    leaf lt {
                                        type types-filter:ttl-or-hop-limit-lt-value;
                                        description "Less than condition match value";
                                    }

                                }
                                case gt {

                                    leaf gt {
                                        type types-filter:ttl-or-hop-limit-gt-value;
                                        description "Greater than condition match value";
                                    }

                                }
                                case range {

                                    container range {
                                        presence "Enable the range context";
                                        description "Enable the range context";

                                        leaf start {
                                            type types-filter:ttl-or-hop-limit-gt-value;
                                            mandatory true;
                                            description "Lower bound of the range";
                                        }

                                        leaf end {
                                            type types-filter:ttl-or-hop-limit-lt-value;
                                            mandatory true;
                                            description "Upper bound of the range";
                                        }

                                    } // container range

                                }
                            }
                        } // container ttl

                    } // container match

                    container action {
                        presence "Enable the action context";
                        description "Enable the action context";

                        leaf fc {
                            type types-sros:fc-name;
                            description "FC name to assign to matching packets";
                        }

                        leaf l2-aware-nat-bypass {
                            type boolean;
                            default "false";
                            description "Divert traffic from an L2-Aware NAT subscriber";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice action {
                            mandatory true;
                            case ignore-match {

                                leaf ignore-match {
                                    type empty;
                                    description "Ignore match criteria for the entry";
                                }

                            }
                            case drop {

                                leaf drop {
                                    type empty;
                                    description "Drop a packet matching this entry";
                                }

                            }
                            case forward {

                                container forward {
                                    description "Enter the forward context";

                                    choice forward-action {
                                        case bonding-connection {

                                            leaf bonding-connection {
                                                type types-submgt:bonding-connection-index;
                                                description "Connection ID over which packet is forwarded";
                                            }

                                        }
                                        case esi-l2 {
                                            status obsolete;

                                            container esi-l2 {
                                                status obsolete;
                                                presence "Enable the esi-l2 context";
                                                description "Enable the esi-l2 context";

                                                leaf esi-value {
                                                    status obsolete;
                                                    type types-services:ethernet-segment-id {
                                                        pattern "(0x[0-9a-fA-F]{20})|([0-9a-fA-F]{2}(:[0-9a-fA-F]{2}){9})|([0-9a-fA-F]{2}(-[0-9a-fA-F]{2}){9})" {
                                                            error-message "'esi-value' must be 10-byte ESI hex (0x... or colon/hyphen octets)";
                                                        }
                                                    }
                                                    mandatory true;
                                                    description "ESI of the first ESI-identified appliance";
                                                }

                                                leaf vpls {
                                                    status obsolete;
                                                    type leafref {
                                                        path "../../../../../../../service/vpls/service-name";
                                                    }
                                                    mandatory true;
                                                    description "VPLS service name";
                                                }

                                            } // container esi-l2

                                        }
                                        case esi-l3 {
                                            status obsolete;

                                            container esi-l3 {
                                                status obsolete;
                                                presence "Enable the esi-l3 context";
                                                description "Enable the esi-l3 context";

                                                leaf sf-ip {
                                                    status obsolete;
                                                    type types-sros:ipv4-address;
                                                    sros-ext:immutable;
                                                    mandatory true;
                                                    description "IP address of the service function to forward traffic";
                                                }

                                                leaf esi-value {
                                                    status obsolete;
                                                    type types-services:ethernet-segment-id {
                                                        pattern "(0x[0-9a-fA-F]{20})|([0-9a-fA-F]{2}(:[0-9a-fA-F]{2}){9})|([0-9a-fA-F]{2}(-[0-9a-fA-F]{2}){9})" {
                                                            error-message "'esi-value' must be 10-byte ESI hex (0x... or colon/hyphen octets)";
                                                        }
                                                    }
                                                    sros-ext:immutable;
                                                    mandatory true;
                                                    description "ESI of the first ESI-identified appliance";
                                                }

                                                leaf vas-interface {
                                                    status obsolete;
                                                    type leafref {
                                                        path "../../../../../../../service/vprn[service-name=current()/../vprn]/interface/interface-name";
                                                    }
                                                    sros-ext:immutable;
                                                    mandatory true;
                                                    description "Egress R-VPLS IP interface name";
                                                }

                                                leaf vprn {
                                                    status obsolete;
                                                    type leafref {
                                                        path "../../../../../../../service/vprn/service-name";
                                                    }
                                                    sros-ext:immutable;
                                                    mandatory true;
                                                    description "VPRN service name";
                                                }

                                            } // container esi-l3

                                        }
                                        case router {

                                            leaf router-instance {
                                                type string;
                                                sros-ext:immutable;
                                                description "Router name or VPRN service name";
                                            }

                                        }
                                        case next-hop {

                                            container next-hop {
                                                presence "Enable the next-hop context";
                                                description "Enable the next-hop context";

                                                choice next-hop {
                                                    mandatory true;
                                                    case nh-ip {

                                                        container nh-ip {
                                                            presence "Enable the nh-ip context";
                                                            description "Enable the nh-ip context";

                                                            leaf indirect {
                                                                type boolean;
                                                                default "false";
                                                                description "Allow next hop to be indirectly reachable";
                                                            }

                                                            leaf address {
                                                                type types-sros:ipv4-address;
                                                                sros-ext:immutable;
                                                                mandatory true;
                                                                description "IPv4 address of next hop to forward matching packets";
                                                            }

                                                        } // container nh-ip

                                                    }
                                                    case nh-interface {
                                                        status obsolete;

                                                        leaf interface-name {
                                                            status obsolete;
                                                            type types-sros:named-item;
                                                            description "IP interface name that forwards matching packets";
                                                        }

                                                    }
                                                    case nh-ip-vrf {

                                                        container nh-ip-vrf {
                                                            presence "Enable the nh-ip-vrf context";
                                                            description "Enable the nh-ip-vrf context";

                                                            leaf indirect {
                                                                type boolean;
                                                                default "false";
                                                                description "Allow next hop to be indirectly reachable";
                                                            }

                                                            leaf router-instance {
                                                                type string;
                                                                sros-ext:immutable;
                                                                mandatory true;
                                                                description "Routing context for route lookup for forwarding packets";
                                                            }

                                                            leaf address {
                                                                type types-sros:ipv4-address;
                                                                sros-ext:immutable;
                                                                mandatory true;
                                                                description "IPv4 address of next hop to forward matching packets";
                                                            }

                                                        } // container nh-ip-vrf

                                                    }
                                                }
                                            } // container next-hop

                                        }
                                        case lsp {

                                            leaf lsp {
                                                type types-sros:named-item-64;
                                                description "LSP that is specified to forward a packet matching this entry";
                                            }

                                        }
                                        case lsp-container {

                                            leaf lsp-container {
                                                type leafref {
                                                    path "../../../../../../router/mpls/lsp-container/container-name";
                                                }
                                                description "LSP container whose members forward matching packets";
                                            }

                                        }
                                        case sdp {

                                            container sdp {
                                                presence "Enable the sdp context";
                                                description "Enable the sdp context";

                                                leaf vpls {
                                                    type leafref {
                                                        path "../../../../../../../service/vpls/service-name";
                                                    }
                                                    mandatory true;
                                                    description "VPLS associated with the SDP";
                                                }

                                                leaf sdp-bind-id {
                                                    type types-services:sdp-bind-id;
                                                    mandatory true;
                                                    description "VPLS SDP bind ID used to forward matching packets";
                                                }

                                            } // container sdp

                                        }
                                        case sap {

                                            container sap {
                                                presence "Enable the sap context";
                                                description "Enable the sap context";

                                                leaf vpls {
                                                    type leafref {
                                                        path "../../../../../../../service/vpls/service-name";
                                                    }
                                                    mandatory true;
                                                    description "VPLS associated with the SAP";
                                                }

                                                leaf sap-id {
                                                    type leafref {
                                                        path "../../../../../../../service/vpls[service-name=current()/../vpls]/sap/sap-id";
                                                    }
                                                    mandatory true;
                                                    description "VPLS Ethernet SAP ID used to forward matching packets";
                                                }

                                            } // container sap

                                        }
                                        case redirect-policy {

                                            leaf redirect-policy {
                                                type leafref {
                                                    path "../../../../../redirect-policy/redirect-policy-name";
                                                }
                                                sros-ext:immutable;
                                                description "Next hop or forward next hop router that forwards a packet that matches this entry";
                                            }

                                        }
                                        case vprn-target {

                                            container vprn-target {
                                                presence "Enable the vprn-target context";
                                                description "Enable the vprn-target context";

                                                leaf bgp-nh {
                                                    type types-sros:ipv4-address {
                                                        pattern "((([0-9]|[1-9][0-9]|1[0-9][0-9]|2[0-4][0-9]|25[0-5])\\.){3}([1-9]|[1-9][0-9]|1[0-9][0-9]|2[0-4][0-9]|25[0-5]))|
                                                                         ((([0-9]|[1-9][0-9]|1[0-9][0-9]|2[0-4][0-9]|25[0-5])\\.){2}(([1-9]|[1-9][0-9]|1[0-9][0-9]|2[0-4][0-9]|25[0-5])\\.){1}([0-9]|[1-9][0-9]|1[0-9][0-9]|2[0-4][0-9]|25[0-5]){1})|
                                                                         ((([0-9]|[1-9][0-9]|1[0-9][0-9]|2[0-4][0-9]|25[0-5])\\.){1}([1-9]|[1-9][0-9]|1[0-9][0-9]|2[0-4][0-9]|25[0-5]){1}(\\.([0-9]|[1-9][0-9]|1[0-9][0-9]|2[0-4][0-9]|25[0-5])){2})|
                                                                         (([1-9]|[1-9][0-9]|1[0-9][0-9]|2[0-4][0-9]|25[0-5]){1}(\\.([0-9]|[1-9][0-9]|1[0-9][0-9]|2[0-4][0-9]|25[0-5])){3})" {
                                                            error-message "'bgp-nh' must be IPv4 unicast (non-zero) in dotted notation";
                                                        }
                                                    }
                                                    mandatory true;
                                                    description "Target BGP next hop IP address";
                                                }

                                                leaf vprn {
                                                    type leafref {
                                                        path "../../../../../../../service/vprn/service-name";
                                                    }
                                                    mandatory true;
                                                    description "Routing context used for route lookup";
                                                }

                                                leaf lsp {
                                                    type types-sros:named-item-64;
                                                    description "LSP that is specified to forward a packet matching this entry";
                                                }

                                                leaf adv-prefix {
                                                    type types-sros:ipv4-prefix;
                                                    description "Advertised IP prefix for target destination";
                                                }

                                            } // container vprn-target

                                        }
                                        case gre-tunnel {

                                            leaf gre-tunnel {
                                                type leafref {
                                                    path "../../../../../gre-tunnel-template/gre-tunnel-template-name";
                                                }
                                                description "GRE tunnel template ID that sets the location where an encapsulated matching packet is transported";
                                            }

                                        }
                                        case mpls-policy {

                                            container mpls-policy {
                                                presence "Enable the mpls-policy context";
                                                description "Enable the mpls-policy context";

                                                leaf endpoint {
                                                    type types-sros:ipv4-unicast-address;
                                                    mandatory true;
                                                    description "MPLS forwarding policy endpoint IPv4 address";
                                                }

                                            } // container mpls-policy

                                        }
                                        case srte-policy {

                                            container srte-policy {
                                                presence "Enable the srte-policy context";
                                                description "Enable the srte-policy context";

                                                leaf endpoint {
                                                    type types-sros:ipv4-unicast-or-zero-address;
                                                    mandatory true;
                                                    description "SR-TE policy endpoint IPv4 address";
                                                }

                                                leaf color {
                                                    type int64 {
                                                        range "0..4294967295";
                                                    }
                                                    mandatory true;
                                                    description "SR-TE policy color ID";
                                                }

                                            } // container srte-policy

                                        }
                                        case srv6-policy {

                                            container srv6-policy {
                                                presence "Enable the srv6-policy context";
                                                description "Enable the srv6-policy context";

                                                leaf endpoint {
                                                    type types-sros:ipv6-unicast-or-zero-address;
                                                    mandatory true;
                                                    description "SRv6 policy endpoint IPv6 address";
                                                }

                                                leaf color {
                                                    type uint32 {
                                                        range "0..4294967295";
                                                    }
                                                    mandatory true;
                                                    description "SRv6 policy color";
                                                }

                                                leaf service-sid {
                                                    type types-sros:ipv6-unicast-address;
                                                    mandatory true;
                                                    description "SRv6 service segment identifier";
                                                }

                                            } // container srv6-policy

                                        }
                                    }
                                } // container forward

                            }
                            case http-redirect {

                                container http-redirect {
                                    presence "Enable the http-redirect context";
                                    description "Enable the http-redirect context";

                                    leaf url {
                                        type union {
                                            type enumeration {
                                                enum from-cpf                       { value 1; }
                                            }
                                            type types-sros:http-redirect-url;
                                        }
                                        sros-ext:immutable;
                                        mandatory true;
                                        description "URL used for HTTP redirect action";
                                    }

                                    leaf allow-override {
                                        type boolean;
                                        default "false";
                                        description "Override the HTTP redirect URL by a RADIUS VSA";
                                    }

                                } // container http-redirect

                            }
                            case nat {

                                container nat {
                                    presence "Enable the nat context";
                                    description "Enable the nat context";

                                    leaf nat-policy {
                                        type leafref {
                                            path "../../../../../../service/nat/nat-policy/name";
                                        }
                                        sros-ext:isa-auto-clear-on-modify;
                                        description "NAT policy name when action is NAT";
                                    }

                                } // container nat

                            }
                            case reassemble {

                                leaf reassemble {
                                    type empty;
                                    description "Forward matching packets to reassembly function";
                                }

                            }
                            case gtp-local-breakout {

                                leaf gtp-local-breakout {
                                    type empty;
                                    description "Break out matching traffic locally from a GTP tunnel for GTP-subscriber-hosts, or forward for other entities";
                                }

                            }
                            case tcp-mss-adjust {

                                leaf tcp-mss-adjust {
                                    type empty;
                                    description "Adjust MSS option of TCP matching packets to configured value of tcp-mss in router interface context";
                                }

                            }
                            case accept {

                                leaf accept {
                                    type empty;
                                    description "Accept regular routing to forward a matching packet";
                                }

                            }
                        }
                        container remark {
                            presence "Enable the remark context";
                            description "Enable the remark context";

                            leaf dscp {
                                type types-qos:dscp-name;
                                mandatory true;
                                description "Destination SAP";
                            }

                        } // container remark

                        container rate-limit {
                            presence "Enable the rate-limit context";
                            description "Enable the rate-limit context";

                            leaf mbs {
                                type union {
                                    type uint32 {
                                        range "0..268435456";
                                    }
                                    type enumeration {
                                        enum auto                           { value -1; }
                                    }
                                }
                                units "bytes";
                                default "auto";
                                description "Maximum burst size";
                            }

                            choice pir-choice {
                                mandatory true;
                                case pir-case {

                                    leaf pir {
                                        type types-filter:rate-limit-pir-kilobps;
                                        units "kilobps";
                                        description "Peak information rate";
                                    }

                                }
                                case pps-pir-case {

                                    leaf pps-pir {
                                        type types-filter:rate-limit-pir-pps;
                                        units "packets per second";
                                        description "Peak information rate";
                                    }

                                }
                                case policer-case {

                                    leaf policer {
                                        type types-sros:named-item;
                                        description "Policer name to use for rate limiting traffic";
                                    }

                                }
                            }
                            choice criterion-1 {
                                case ttl {

                                    container ttl {
                                        presence "Enable the ttl context";
                                        description "Enable the ttl context";

                                        choice ttl {
                                            mandatory true;
                                            case eq {

                                                leaf eq {
                                                    type types-filter:ttl-or-hop-limit-value;
                                                    description "Equal to condition match value";
                                                }

                                            }
                                            case lt {

                                                leaf lt {
                                                    type types-filter:ttl-or-hop-limit-lt-value;
                                                    description "Less than condition match value";
                                                }

                                            }
                                            case gt {

                                                leaf gt {
                                                    type types-filter:ttl-or-hop-limit-gt-value;
                                                    description "Greater than condition match value";
                                                }

                                            }
                                            case range {

                                                container range {
                                                    presence "Enable the range context";
                                                    description "Enable the range context";

                                                    leaf start {
                                                        type types-filter:ttl-or-hop-limit-gt-value;
                                                        mandatory true;
                                                        description "Lower bound of the range";
                                                    }

                                                    leaf end {
                                                        type types-filter:ttl-or-hop-limit-lt-value;
                                                        mandatory true;
                                                        description "Upper bound of the range";
                                                    }

                                                } // container range

                                            }
                                        }
                                    } // container ttl

                                }
                                case packet-length {

                                    container packet-length {
                                        presence "Enable the packet-length context";
                                        description "Enable the packet-length context";

                                        choice packet-length {
                                            mandatory true;
                                            case eq {

                                                leaf eq {
                                                    type types-filter:pkt-len-or-payload-len-value;
                                                    description "Exact match criterion for the length";
                                                }

                                            }
                                            case lt {

                                                leaf lt {
                                                    type types-filter:pkt-len-or-payload-len-lt-value;
                                                    description "Less than match criterion for the length";
                                                }

                                            }
                                            case gt {

                                                leaf gt {
                                                    type types-filter:pkt-len-or-payload-len-gt-value;
                                                    description "Greater than match criterion for the length";
                                                }

                                            }
                                            case range {

                                                container range {
                                                    presence "Enable the range context";
                                                    description "Enable the range context";

                                                    leaf start {
                                                        type types-filter:pkt-len-or-payload-len-gt-value;
                                                        mandatory true;
                                                        description "Lower bound of the length range";
                                                    }

                                                    leaf end {
                                                        type types-filter:pkt-len-or-payload-len-lt-value;
                                                        mandatory true;
                                                        description "Upper bound of the length range";
                                                    }

                                                } // container range

                                            }
                                        }
                                    } // container packet-length

                                }
                            }
                            choice choice2 {
                                case extracted-traffic-case {

                                    leaf extracted-traffic {
                                        type empty;
                                        description "Limit the rate of traffic extracted to the CPM";
                                    }

                                }
                            }
                            container pattern {
                                presence "Enable the pattern context";
                                description "Enable the pattern context";

                                leaf expression {
                                    type types-sros:hex-string {
                                        length "3..18";
                                    }
                                    mandatory true;
                                    description "Pattern expression to match";
                                }

                                leaf mask {
                                    type types-sros:hex-string {
                                        length "3..18";
                                        pattern "0x[a-fA-F0-9]*[a-fA-F1-9]+[a-fA-F0-9]*" {
                                            error-message "'mask' must be 0x-prefixed hex and not all zeros (e.g. 0x1a2b)";
                                        }
                                    }
                                    mandatory true;
                                    description "Mask for the pattern expression";
                                }

                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                leaf offset-value {
                                    type int32 {
                                        range "0..255";
                                    }
                                    mandatory true;
                                    description "Offset value for the pattern expression";
                                }

                            } // container pattern

                        } // container rate-limit

                        container drop-when {
                            presence "Enable the drop-when context";
                            description "Enable the drop-when context";

                            choice criterion-1 {
                                case ttl {

                                    container ttl {
                                        presence "Enable the ttl context";
                                        description "Enable the ttl context";

                                        choice ttl {
                                            mandatory true;
                                            case eq {

                                                leaf eq {
                                                    type types-filter:ttl-or-hop-limit-value;
                                                    description "Equal to condition match value";
                                                }

                                            }
                                            case lt {

                                                leaf lt {
                                                    type types-filter:ttl-or-hop-limit-lt-value;
                                                    description "Less than condition match value";
                                                }

                                            }
                                            case gt {

                                                leaf gt {
                                                    type types-filter:ttl-or-hop-limit-gt-value;
                                                    description "Greater than condition match value";
                                                }

                                            }
                                            case range {

                                                container range {
                                                    presence "Enable the range context";
                                                    description "Enable the range context";

                                                    leaf start {
                                                        type types-filter:ttl-or-hop-limit-gt-value;
                                                        mandatory true;
                                                        description "Lower bound of the range";
                                                    }

                                                    leaf end {
                                                        type types-filter:ttl-or-hop-limit-lt-value;
                                                        mandatory true;
                                                        description "Upper bound of the range";
                                                    }

                                                } // container range

                                            }
                                        }
                                    } // container ttl

                                }
                                case packet-length {

                                    container packet-length {
                                        presence "Enable the packet-length context";
                                        description "Enable the packet-length context";

                                        choice packet-length {
                                            mandatory true;
                                            case eq {

                                                leaf eq {
                                                    type types-filter:pkt-len-or-payload-len-value;
                                                    description "Exact match criterion for the length";
                                                }

                                            }
                                            case lt {

                                                leaf lt {
                                                    type types-filter:pkt-len-or-payload-len-lt-value;
                                                    description "Less than match criterion for the length";
                                                }

                                            }
                                            case gt {

                                                leaf gt {
                                                    type types-filter:pkt-len-or-payload-len-gt-value;
                                                    description "Greater than match criterion for the length";
                                                }

                                            }
                                            case range {

                                                container range {
                                                    presence "Enable the range context";
                                                    description "Enable the range context";

                                                    leaf start {
                                                        type types-filter:pkt-len-or-payload-len-gt-value;
                                                        mandatory true;
                                                        description "Lower bound of the length range";
                                                    }

                                                    leaf end {
                                                        type types-filter:pkt-len-or-payload-len-lt-value;
                                                        mandatory true;
                                                        description "Upper bound of the length range";
                                                    }

                                                } // container range

                                            }
                                        }
                                    } // container packet-length

                                }
                            }
                            choice criterion-2 {
                                case extracted-traffic {

                                    leaf extracted-traffic {
                                        type empty;
                                        description "Drop traffic extracted to CPM";
                                    }

                                }
                            }
                            container pattern {
                                presence "Enable the pattern context";
                                description "Enable the pattern context";

                                leaf expression {
                                    type types-sros:hex-string {
                                        length "3..18";
                                    }
                                    mandatory true;
                                    description "Pattern expression to match";
                                }

                                leaf mask {
                                    type types-sros:hex-string {
                                        length "3..18";
                                        pattern "0x[a-fA-F0-9]*[a-fA-F1-9]+[a-fA-F0-9]*" {
                                            error-message "'mask' must be 0x-prefixed hex and not all zeros (e.g. 0x1a2b)";
                                        }
                                    }
                                    mandatory true;
                                    description "Mask for the pattern expression";
                                }

                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                leaf offset-value {
                                    type int32 {
                                        range "0..255";
                                    }
                                    mandatory true;
                                    description "Offset value for the pattern expression";
                                }

                            } // container pattern

                        } // container drop-when

                        container accept-when {
                            presence "Enable the accept-when context";
                            description "Enable the accept-when context";

                            container pattern {
                                presence "Enable the pattern context";
                                description "Enable the pattern context";

                                leaf expression {
                                    type types-sros:hex-string {
                                        length "3..18";
                                    }
                                    mandatory true;
                                    description "Pattern expression to match";
                                }

                                leaf mask {
                                    type types-sros:hex-string {
                                        length "3..18";
                                        pattern "0x[a-fA-F0-9]*[a-fA-F1-9]+[a-fA-F0-9]*" {
                                            error-message "'mask' must be 0x-prefixed hex and not all zeros (e.g. 0x1a2b)";
                                        }
                                    }
                                    mandatory true;
                                    description "Mask for the pattern expression";
                                }

                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                leaf offset-value {
                                    type int32 {
                                        range "0..255";
                                    }
                                    mandatory true;
                                    description "Offset value for the pattern expression";
                                }

                            } // container pattern

                        } // container accept-when

                        container secondary {
                            presence "Enable the secondary context";
                            description "Enable the secondary context";

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice action {
                                mandatory true;
                                case forward {

                                    container forward {
                                        description "Enter the forward context";

                                        choice forward-action {
                                            case next-hop {

                                                container next-hop {
                                                    presence "Enable the next-hop context";
                                                    description "Enable the next-hop context";

                                                    choice next-hop {
                                                        mandatory true;
                                                        case nh-ip-vrf {

                                                            container nh-ip-vrf {
                                                                presence "Enable the nh-ip-vrf context";
                                                                description "Enable the nh-ip-vrf context";

                                                                leaf indirect {
                                                                    type boolean;
                                                                    default "false";
                                                                    description "Allow next hop to be indirectly reachable";
                                                                }

                                                                leaf router-instance {
                                                                    type string;
                                                                    sros-ext:immutable;
                                                                    mandatory true;
                                                                    description "Routing context for route lookup for forwarding packets";
                                                                }

                                                                leaf address {
                                                                    type types-sros:ipv4-address;
                                                                    sros-ext:immutable;
                                                                    mandatory true;
                                                                    description "IPv4 address of next hop to forward matching packets";
                                                                }

                                                            } // container nh-ip-vrf

                                                        }
                                                    }
                                                } // container next-hop

                                            }
                                            case sdp {

                                                container sdp {
                                                    presence "Enable the sdp context";
                                                    description "Enable the sdp context";

                                                    leaf vpls {
                                                        type leafref {
                                                            path "../../../../../../../../service/vpls/service-name";
                                                        }
                                                        mandatory true;
                                                        description "VPLS associated with the SDP";
                                                    }

                                                    leaf sdp-bind-id {
                                                        type types-services:sdp-bind-id;
                                                        sros-ext:immutable;
                                                        mandatory true;
                                                        description "VPLS SDP bind ID used to forward matching packets";
                                                    }

                                                } // container sdp

                                            }
                                            case sap {

                                                container sap {
                                                    presence "Enable the sap context";
                                                    description "Enable the sap context";

                                                    leaf vpls {
                                                        type leafref {
                                                            path "../../../../../../../../service/vpls/service-name";
                                                        }
                                                        mandatory true;
                                                        description "VPLS the sdp-bind-id belongs to";
                                                    }

                                                    leaf sap-id {
                                                        type leafref {
                                                            path "../../../../../../../../service/vpls[service-name=current()/../vpls]/sap/sap-id";
                                                        }
                                                        sros-ext:immutable;
                                                        mandatory true;
                                                        description "SAP ID used to forward packets matching the entry";
                                                    }

                                                } // container sap

                                            }
                                            case vprn-target {

                                                container vprn-target {
                                                    presence "Enable the vprn-target context";
                                                    description "Enable the vprn-target context";

                                                    leaf bgp-nh {
                                                        type types-sros:ipv4-address {
                                                            pattern "((([0-9]|[1-9][0-9]|1[0-9][0-9]|2[0-4][0-9]|25[0-5])\\.){3}([1-9]|[1-9][0-9]|1[0-9][0-9]|2[0-4][0-9]|25[0-5]))|
                                                                             ((([0-9]|[1-9][0-9]|1[0-9][0-9]|2[0-4][0-9]|25[0-5])\\.){2}(([1-9]|[1-9][0-9]|1[0-9][0-9]|2[0-4][0-9]|25[0-5])\\.){1}([0-9]|[1-9][0-9]|1[0-9][0-9]|2[0-4][0-9]|25[0-5]){1})|
                                                                             ((([0-9]|[1-9][0-9]|1[0-9][0-9]|2[0-4][0-9]|25[0-5])\\.){1}([1-9]|[1-9][0-9]|1[0-9][0-9]|2[0-4][0-9]|25[0-5]){1}(\\.([0-9]|[1-9][0-9]|1[0-9][0-9]|2[0-4][0-9]|25[0-5])){2})|
                                                                             (([1-9]|[1-9][0-9]|1[0-9][0-9]|2[0-4][0-9]|25[0-5]){1}(\\.([0-9]|[1-9][0-9]|1[0-9][0-9]|2[0-4][0-9]|25[0-5])){3})" {
                                                                error-message "'bgp-nh' must be IPv4 unicast (non-zero) in dotted notation";
                                                            }
                                                        }
                                                        mandatory true;
                                                        description "Target BGP next hop IP address";
                                                    }

                                                    leaf vprn {
                                                        type leafref {
                                                            path "../../../../../../../../service/vprn/service-name";
                                                        }
                                                        mandatory true;
                                                        description "Routing context used for route lookup";
                                                    }

                                                    leaf lsp {
                                                        type types-sros:named-item-64;
                                                        description "LSP that is specified to forward a packet matching this entry";
                                                    }

                                                    leaf adv-prefix {
                                                        type types-sros:ipv4-prefix;
                                                        description "Advertised IP prefix for the target destination";
                                                    }

                                                } // container vprn-target

                                            }
                                        }
                                    } // container forward

                                }
                            }
                            container remark {
                                presence "Enable the remark context";
                                description "Enable the remark context";

                                leaf dscp {
                                    type types-qos:dscp-name;
                                    mandatory true;
                                    description "Destination SAP";
                                }

                            } // container remark

                        } // container secondary

                    } // container action

                } // list entry

                container embed {
                    description "Enter the embed context";

                    list filter {
                        key "name offset";
                        description "Enter the filter list instance";

                        leaf name {
                            type leafref {
                                path "../../../../ip-filter/filter-name";
                            }
                            description "IPv4 policy to be embedded in the filter";
                        }

                        leaf offset {
                            type types-filter:embed-offset {
                                range "0..2097150";
                            }
                            description "Offset of the embedded filter policy";
                        }

                        leaf admin-state {
                            type types-sros:admin-state;
                            default "enable";
                            description "Administrative state of the embedded filter";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list filter

                    list flowspec {
                        key "offset";
                        description "Enter the flowspec list instance";

                        leaf offset {
                            type types-filter:embed-offset;
                            description "Offset of the inserted entries";
                        }

                        leaf group {
                            type uint32 {
                                range "0..16383";
                            }
                            sros-ext:immutable;
                            description "Group ID of FlowSpec routes to embed in the filter";
                        }

                        leaf router-instance {
                            type string;
                            sros-ext:immutable;
                            mandatory true;
                            description "Routing instance source of BGP FlowSpec routes";
                        }

                        leaf admin-state {
                            type types-sros:admin-state;
                            default "enable";
                            description "Administrative state of the embedded filter";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list flowspec

                    list openflow {
                        status obsolete;
                        key "of-switch offset";
                        description "Enter the openflow list instance";

                        leaf of-switch {
                            status obsolete;
                            type types-sros:named-item;
                            description "Referenced Hybrid OpenFlow Switch (OFS) name";
                        }

                        leaf offset {
                            status obsolete;
                            type types-filter:embed-offset {
                                range "0..2097150";
                            }
                            description "Offset of the embedded filter policy";
                        }

                        leaf admin-state {
                            status obsolete;
                            type types-sros:admin-state;
                            default "enable";
                            description "Administrative state of the embedded filter";
                        }

                        leaf-list apply-groups {
                            status obsolete;
                            type leafref {
                                path "../../../../../groups/group/name";
                            }
                            max-elements 8;
                            ordered-by user;
                            description "Apply a configuration group at this level";
                        }

                        leaf-list apply-groups-exclude {
                            status obsolete;
                            type leafref {
                                path "../../../../../groups/group/name";
                            }
                            max-elements 8;
                            ordered-by user;
                            description "Exclude a configuration group at this level";
                        }

                        choice context {
                            status obsolete;
                            default "grt";
                            description
                                "Specifies the context in which the openflow embedding is inserted into filter.
                                 When no context is present, this object is set to grt value.";
                            case grt {
                                status obsolete;

                                leaf grt {
                                    status obsolete;
                                    type empty;
                                    sros-ext:immutable;
                                    description "Global routing context";
                                }

                            }
                            case system {
                                status obsolete;

                                leaf system {
                                    status obsolete;
                                    type empty;
                                    sros-ext:immutable;
                                    description "System context";
                                }

                            }
                            case vprn {
                                status obsolete;

                                leaf vprn {
                                    status obsolete;
                                    type leafref {
                                        path "../../../../../service/vprn/service-name";
                                    }
                                    sros-ext:immutable;
                                    description "VPRN context";
                                }

                            }
                            case vpls {
                                status obsolete;

                                leaf vpls {
                                    status obsolete;
                                    type leafref {
                                        path "../../../../../service/vpls/service-name";
                                    }
                                    sros-ext:immutable;
                                    description "VPLS context";
                                }

                                leaf sap {
                                    status obsolete;
                                    type leafref {
                                        path "../../../../../service/vpls[service-name=current()/../vpls]/sap/sap-id";
                                    }
                                    sros-ext:immutable;
                                    description "SAP context";
                                }

                            }
                        }
                    } // list openflow

                } // container embed

            } // list ip-filter

            list ipv6-filter {
                key "filter-name";
                description "Enter the ipv6-filter list instance";

                leaf filter-name {
                    type types-filter:filter-name;
                    description "Filter name";
                }

                leaf default-action {
                    type types-filter:filter-default-action;
                    default "drop";
                    description "Action for packets that do not match any entry";
                }

                leaf description {
                    type types-sros:description;
                    description "Text description";
                }

                leaf scope {
                    type types-filter:filter-scope;
                    default "template";
                    description "Scope of the filter definition";
                }

                leaf type {
                    type enumeration {
                        enum normal                         { value 0; }
                        enum src-mac                        { value 1; }
                        enum packet-length                  { value 2; }
                        enum destination-class              { value 3; }
                    }
                    default "normal";
                    description "Set of match criteria for the filter policy";
                }

                leaf chain-to-system-filter {
                    type boolean;
                    default "false";
                    description "Chain filter policy to the active IPvX system filter policy";
                }

                leaf shared-policer {
                    type boolean;
                    default "false";
                    description "Share policer among active ports in the LAG";
                }

                leaf filter-id {
                    type types-filter:filter-id;
                    sros-ext:immutable;
                    description "IPv6 filter identifier";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container subscriber-mgmt {
                    description "Enter the subscriber-mgmt context";

                    container host-specific-entry {
                        description "Enter the host-specific-entry context";

                        container filter-rule {
                            description "Enter the filter-rule context";

                            container range {
                                presence "Enable the range context";
                                description "Enable the range context";

                                leaf start {
                                    type types-filter:entry-id;
                                    mandatory true;
                                    description "Lower bound of range for inserting filter rule entries";
                                }

                                leaf end {
                                    type types-filter:entry-id;
                                    mandatory true;
                                    description "Upper bound of range for inserting filter rule entries";
                                }

                            } // container range

                        } // container filter-rule

                        container credit-control {
                            description "Enter the credit-control context";

                            container range {
                                presence "Enable the range context";
                                description "Enable the range context";

                                leaf start {
                                    type types-filter:entry-id;
                                    mandatory true;
                                    description "Lower bound of range for credit control filter entries";
                                }

                                leaf end {
                                    type types-filter:entry-id;
                                    mandatory true;
                                    description "Upper bound of range for credit control filter entries";
                                }

                            } // container range

                        } // container credit-control

                        container watermark {
                            description "Enter the watermark context";

                            leaf low {
                                type int32 {
                                    range "0..100";
                                }
                                default "90";
                                description "Low watermark for host-specific entries, to clear a table full alarm";
                            }

                            leaf high {
                                type int32 {
                                    range "0..100";
                                }
                                default "95";
                                description "High watermark for host-specific entries, to raise a table full alarm";
                            }

                        } // container watermark

                    } // container host-specific-entry

                    container shared-entry {
                        description "Enter the shared-entry context";

                        container filter-rule {
                            description "Enter the filter-rule context";

                            container range {
                                presence "Enable the range context";
                                description "Enable the range context";

                                leaf start {
                                    type types-filter:entry-id;
                                    mandatory true;
                                    description "Lower bound of range for inserting shared host rules";
                                }

                                leaf end {
                                    type types-filter:entry-id;
                                    mandatory true;
                                    description "Upper bound of range for inserting shared host rules";
                                }

                            } // container range

                        } // container filter-rule

                        container pcc-rule {
                            description "Enter the pcc-rule context";

                            container range {
                                presence "Enable the range context";
                                description "Enable the range context";

                                leaf start {
                                    type types-filter:entry-id;
                                    mandatory true;
                                    description "Lower bound of the range for PCC rule filter entries";
                                }

                                leaf end {
                                    type types-filter:entry-id;
                                    mandatory true;
                                    description "Upper bound of the range for PCC rule filter entries";
                                }

                            } // container range

                        } // container pcc-rule

                        container watermark {
                            presence "Enable the watermark context";
                            description "Enable the watermark context";

                            leaf low {
                                type int32 {
                                    range "0..7999";
                                }
                                mandatory true;
                                description "Limit of RADIUS or Diameter shared filters before clearing high watermark notification";
                            }

                            leaf high {
                                type int32 {
                                    range "1..8000";
                                }
                                mandatory true;
                                description "Limit of RADIUS shared filters before generating high watermark notification";
                            }

                        } // container watermark

                    } // container shared-entry

                } // container subscriber-mgmt

                list entry {
                    key "entry-id";
                    description "Enter the entry list instance";

                    leaf entry-id {
                        type types-filter:entry-id;
                        description "ID for a match criteria and the corresponding action";
                    }

                    leaf description {
                        type types-sros:description;
                        description "Text description";
                    }

                    leaf pbr-down-action-override {
                        type types-filter:filter-pbr-down-action-ovr;
                        description "Action when PBR or PBF target for this entry is not available";
                    }

                    leaf sticky-dest {
                        type types-filter:filter-sticky-dest;
                        units "seconds";
                        description "Time before action with available PBR or PBF destination and highest priority";
                    }

                    leaf log {
                        type leafref {
                            path "../../../log/log-id";
                        }
                        description "Log that is used for packets matching this entry";
                    }

                    leaf collect-stats {
                        type boolean;
                        default "false";
                        description "Enable statistics collection for an entry";
                    }

                    leaf egress-pbr {
                        type types-filter:filter-egress-pbr;
                        sros-ext:immutable;
                        description "PBR that has an effect when this filter is applied on egress";
                    }

                    leaf filter-sample {
                        type boolean;
                        default "false";
                        description "Sample matching traffic if IP interface is set to cflowd ACL mode";
                    }

                    leaf interface-sample {
                        type boolean;
                        default "true";
                        description "Sample matching traffic if IP interface is set to cflowd interface mode";
                    }

                    leaf sample-profile {
                        type leafref {
                            path "../../../../cflowd/sample-profile/profile-id";
                        }
                        description "Cflowd sample profile ID to match packets";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container match {
                        description "Enter the match context";

                        leaf dscp {
                            type types-qos:dscp-name;
                            description "DSCP used as an IP filter match criterion";
                        }

                        leaf fragment {
                            type enumeration {
                                enum false                          { value 2; }
                                enum true                           { value 3; }
                                enum first-only                     { value 4; }
                                enum non-first-only                 { value 5; }
                            }
                            description "Match criterion for fragmented packages";
                        }

                        leaf destination-class {
                            type types-sros:class-index;
                            description "Destination class as a match criterion";
                        }

                        choice match-next-header-choice {
                            case next-header {

                                leaf next-header {
                                    type types-sros:match-ip-protocol;
                                    description "IP protocol to match";
                                }

                            }
                            case next-header-list {

                                leaf-list next-header-list {
                                    type leafref {
                                        path "../../../../match-list/protocol-list/protocol-list-name";
                                    }
                                    max-elements 16;
                                    description "Name of the protocol list as a match criterion";
                                }

                            }
                        }
                        choice ip-selector {
                            case src-dst-ip {

                                container src-ip {
                                    description "Enter the src-ip context";

                                    choice match-address-choice {
                                        case address-and-prefix-or-mask {

                                            leaf address {
                                                type union {
                                                    type types-sros:ipv6-prefix-with-host-bits;
                                                    type types-sros:ipv6-address;
                                                }
                                                description "IPv6 address used as the match criterion";
                                            }

                                            leaf mask {
                                                type types-sros:ipv6-address;
                                                description "IPv6 address mask used as the match criterion";
                                            }

                                        }
                                        case ipv6-prefix-list {

                                            leaf-list ipv6-prefix-list {
                                                type leafref {
                                                    path "../../../../../match-list/ipv6-prefix-list/prefix-list-name";
                                                }
                                                max-elements 16;
                                                description "IPv6 address prefix list used as match criterion";
                                            }

                                        }
                                    }
                                } // container src-ip

                                container dst-ip {
                                    description "Enter the dst-ip context";

                                    choice match-address-choice {
                                        case address-and-prefix-or-mask {

                                            leaf address {
                                                type union {
                                                    type types-sros:ipv6-prefix-with-host-bits;
                                                    type types-sros:ipv6-address;
                                                }
                                                description "IPv6 address used as the match criterion";
                                            }

                                            leaf mask {
                                                type types-sros:ipv6-address;
                                                description "IPv6 address mask used as the match criterion";
                                            }

                                        }
                                        case ipv6-prefix-list {

                                            leaf-list ipv6-prefix-list {
                                                type leafref {
                                                    path "../../../../../match-list/ipv6-prefix-list/prefix-list-name";
                                                }
                                                max-elements 16;
                                                description "IPv6 address prefix list used as match criterion";
                                            }

                                        }
                                    }
                                } // container dst-ip

                            }
                            case ip {

                                container ip {
                                    description "Enter the ip context";

                                    choice match-address-choice {
                                        case address-and-prefix-or-mask {

                                            leaf address {
                                                type union {
                                                    type types-sros:ipv6-prefix-with-host-bits;
                                                    type types-sros:ipv6-address;
                                                }
                                                description "IPv6 address used as the match criterion";
                                            }

                                            leaf mask {
                                                type types-sros:ipv6-address;
                                                description "IPv6 address mask used as the match criterion";
                                            }

                                        }
                                        case ipv6-prefix-list {

                                            leaf-list ipv6-prefix-list {
                                                type leafref {
                                                    path "../../../../../match-list/ipv6-prefix-list/prefix-list-name";
                                                }
                                                max-elements 16;
                                                description "IPv6 address prefix list used as match criterion";
                                            }

                                        }
                                    }
                                } // container ip

                            }
                        }
                        choice port-selector {
                            case src-dst-port {

                                container src-port {
                                    description "Enter the src-port context";

                                    choice port {
                                        case eq {

                                            leaf eq {
                                                type uint16 {
                                                    range "0..65535";
                                                }
                                                description "Exact value as the match criterion";
                                            }

                                        }
                                        case lt {

                                            leaf lt {
                                                type uint16 {
                                                    range "1..65535";
                                                }
                                                description "Less than value as the match criterion";
                                            }

                                        }
                                        case gt {

                                            leaf gt {
                                                type uint16 {
                                                    range "0..65534";
                                                }
                                                description "Greater than value as the match criterion";
                                            }

                                        }
                                        case range {

                                            container range {
                                                presence "Enable the range context";
                                                description "Enable the range context";

                                                leaf start {
                                                    type uint16 {
                                                        range "0..65534";
                                                    }
                                                    mandatory true;
                                                    description "Lower bound of the port range";
                                                }

                                                leaf end {
                                                    type uint16 {
                                                        range "1..65535";
                                                    }
                                                    mandatory true;
                                                    description "Upper bound of the port range";
                                                }

                                            } // container range

                                        }
                                        case port-list {

                                            leaf-list port-list {
                                                type leafref {
                                                    path "../../../../../match-list/port-list/port-list-name";
                                                }
                                                max-elements 16;
                                                description "Name of the port list as the match criterion";
                                            }

                                        }
                                    }
                                } // container src-port

                                container dst-port {
                                    description "Enter the dst-port context";

                                    choice port {
                                        case eq {

                                            leaf eq {
                                                type uint16 {
                                                    range "0..65535";
                                                }
                                                description "Exact value as the match criterion";
                                            }

                                        }
                                        case lt {

                                            leaf lt {
                                                type uint16 {
                                                    range "1..65535";
                                                }
                                                description "Less than value as the match criterion";
                                            }

                                        }
                                        case gt {

                                            leaf gt {
                                                type uint16 {
                                                    range "0..65534";
                                                }
                                                description "Greater than value as the match criterion";
                                            }

                                        }
                                        case range {

                                            container range {
                                                presence "Enable the range context";
                                                description "Enable the range context";

                                                leaf start {
                                                    type uint16 {
                                                        range "0..65534";
                                                    }
                                                    mandatory true;
                                                    description "Lower bound of the port range";
                                                }

                                                leaf end {
                                                    type uint16 {
                                                        range "1..65535";
                                                    }
                                                    mandatory true;
                                                    description "Upper bound of the port range";
                                                }

                                            } // container range

                                        }
                                        case port-list {

                                            leaf-list port-list {
                                                type leafref {
                                                    path "../../../../../match-list/port-list/port-list-name";
                                                }
                                                max-elements 16;
                                                description "Name of the port list as the match criterion";
                                            }

                                        }
                                    }
                                } // container dst-port

                            }
                            case port {

                                container port {
                                    description "Enter the port context";

                                    choice port {
                                        case eq {

                                            leaf eq {
                                                type uint16 {
                                                    range "0..65535";
                                                }
                                                description "Exact value as the match criterion";
                                            }

                                        }
                                        case lt {

                                            leaf lt {
                                                type uint16 {
                                                    range "1..65535";
                                                }
                                                description "Less than value as the match criterion";
                                            }

                                        }
                                        case gt {

                                            leaf gt {
                                                type uint16 {
                                                    range "0..65534";
                                                }
                                                description "Greater than value as the match criterion";
                                            }

                                        }
                                        case range {

                                            container range {
                                                presence "Enable the range context";
                                                description "Enable the range context";

                                                leaf start {
                                                    type uint16 {
                                                        range "0..65534";
                                                    }
                                                    mandatory true;
                                                    description "Lower bound of the port range";
                                                }

                                                leaf end {
                                                    type uint16 {
                                                        range "1..65535";
                                                    }
                                                    mandatory true;
                                                    description "Upper bound of the port range";
                                                }

                                            } // container range

                                        }
                                        case port-list {

                                            leaf-list port-list {
                                                type leafref {
                                                    path "../../../../../match-list/port-list/port-list-name";
                                                }
                                                max-elements 16;
                                                description "Name of the port list as the match criterion";
                                            }

                                        }
                                    }
                                } // container port

                            }
                        }
                        choice match-tcp-flags {
                            case tcp-established {

                                leaf tcp-established {
                                    type empty;
                                    description "Use ACK or RST status in TCP header as match criterion";
                                }

                            }
                            case tcp-flags {

                                container tcp-flags {
                                    description "Enter the tcp-flags context";

                                    leaf ack {
                                        type boolean;
                                        description "Use ACK TCP bit status in TCP header as match criterion";
                                    }

                                    leaf syn {
                                        type boolean;
                                        description "Use SYN TCP bit status in TCP header as match criterion";
                                    }

                                    leaf fin {
                                        type boolean;
                                        description "Use FIN TCP bit status in TCP header as match criterion";
                                    }

                                    leaf rst {
                                        type boolean;
                                        description "Use RST TCP bit status in TCP header as match criterion";
                                    }

                                    leaf psh {
                                        type boolean;
                                        description "Use PSH TCP bit status in TCP header as match criterion";
                                    }

                                    leaf urg {
                                        type boolean;
                                        description "Use URG TCP bit status in TCP header as match criterion";
                                    }

                                    leaf ece {
                                        type boolean;
                                        description "Use ECE TCP bit status in TCP header as match criterion";
                                    }

                                    leaf cwr {
                                        type boolean;
                                        description "Use CWR TCP bit status in TCP header as match criterion";
                                    }

                                    leaf ns {
                                        type boolean;
                                        description "Use NS TCP bit status in TCP header as match criterion";
                                    }

                                } // container tcp-flags

                            }
                        }
                        container src-mac {
                            presence "Enable the src-mac context";
                            description "Enable the src-mac context";

                            leaf address {
                                type yang:mac-address;
                                mandatory true;
                                description "MAC address used as the match criterion";
                            }

                            leaf mask {
                                type yang:mac-address;
                                default "ff:ff:ff:ff:ff:ff";
                                description "MAC address mask as the match criterion";
                            }

                        } // container src-mac

                        container extension-header {
                            description "Enter the extension-header context";

                            leaf ah {
                                type boolean;
                                description "Match a packet as per the existence of an AH Extension Header";
                            }

                            leaf esp {
                                type boolean;
                                description "Match a packet as per the existence of an Encapsulation security payload extension header";
                            }

                            leaf hop-by-hop {
                                type boolean;
                                description "Match on Hop-by-Hop Options Extension Header existence";
                            }

                            leaf routing-type0 {
                                type boolean;
                                description "Match a packet as per the existence of a routing Extension Header";
                            }

                            leaf routing-type4 {
                                type boolean;
                                description "Match on routing extension header type 4 existence";
                            }

                        } // container extension-header

                        container flow-label {
                            presence "Enable the flow-label context";
                            description "Enable the flow-label context";

                            leaf value {
                                type types-filter:filter-match-flow-label;
                                mandatory true;
                                description "Flow label as a match criterion";
                            }

                            leaf mask {
                                type types-filter:filter-match-flow-label {
                                    range "1..1048575";
                                }
                                default "1048575";
                                description "Flow label mask for the IPv6 filter entry";
                            }

                        } // container flow-label

                        container icmp {
                            description "Enter the icmp context";

                            choice icmp-code {
                                case code {

                                    leaf code {
                                        type types-filter:ipv6-match-icmp-codes;
                                        description "ICMPv6 code value to match";
                                    }

                                }
                            }
                            choice icmp-type {
                                case type {

                                    leaf type {
                                        type types-filter:ipv6-match-icmp-types;
                                        description "ICMPv6 type value to match";
                                    }

                                }
                            }
                        } // container icmp

                        container packet-length {
                            presence "Enable the packet-length context";
                            description "Enable the packet-length context";

                            choice packet-length {
                                mandatory true;
                                case eq {

                                    leaf eq {
                                        type types-filter:ipv6-match-packet-length-value;
                                        description "Exact match criterion for the length";
                                    }

                                }
                                case lt {

                                    leaf lt {
                                        type types-filter:ipv6-match-packet-length-lt-value;
                                        description "Less than match criterion for the length";
                                    }

                                }
                                case gt {

                                    leaf gt {
                                        type types-filter:ipv6-match-packet-length-gt-value;
                                        description "Greater than match criterion for the length";
                                    }

                                }
                                case range {

                                    container range {
                                        presence "Enable the range context";
                                        description "Enable the range context";

                                        leaf start {
                                            type types-filter:ipv6-match-packet-length-gt-value;
                                            mandatory true;
                                            description "Lower bound of packet length range as match criterion";
                                        }

                                        leaf end {
                                            type types-filter:ipv6-match-packet-length-lt-value;
                                            mandatory true;
                                            description "Upper bound of packet length range as match criterion";
                                        }

                                    } // container range

                                }
                                case ipv6-packet-length-list {

                                    leaf-list ipv6-packet-length-list {
                                        type leafref {
                                            path "../../../../../match-list/ipv6-packet-length-list/packet-length-list-name";
                                        }
                                        max-elements 16;
                                        description "IPv6 packet length list to match";
                                    }

                                }
                            }
                        } // container packet-length

                        container hop-limit {
                            presence "Enable the hop-limit context";
                            description "Enable the hop-limit context";

                            choice hop-limit {
                                mandatory true;
                                case eq {

                                    leaf eq {
                                        type types-filter:ttl-or-hop-limit-value;
                                        description "Equal to condition match value";
                                    }

                                }
                                case lt {

                                    leaf lt {
                                        type types-filter:ttl-or-hop-limit-lt-value;
                                        description "Less than condition match value";
                                    }

                                }
                                case gt {

                                    leaf gt {
                                        type types-filter:ttl-or-hop-limit-gt-value;
                                        description "Greater than condition match value";
                                    }

                                }
                                case range {

                                    container range {
                                        presence "Enable the range context";
                                        description "Enable the range context";

                                        leaf start {
                                            type types-filter:ttl-or-hop-limit-gt-value;
                                            mandatory true;
                                            description "Lower bound of the range";
                                        }

                                        leaf end {
                                            type types-filter:ttl-or-hop-limit-lt-value;
                                            mandatory true;
                                            description "Upper bound of the range";
                                        }

                                    } // container range

                                }
                            }
                        } // container hop-limit

                    } // container match

                    container action {
                        presence "Enable the action context";
                        description "Enable the action context";

                        leaf fc {
                            type types-sros:fc-name;
                            description "FC name to assign to matching packets";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice action {
                            mandatory true;
                            case ignore-match {

                                leaf ignore-match {
                                    type empty;
                                    description "Ignore match criteria for the entry";
                                }

                            }
                            case drop {

                                leaf drop {
                                    type empty;
                                    description "Drop a packet matching this entry";
                                }

                            }
                            case forward {

                                container forward {
                                    description "Enter the forward context";

                                    choice forward-action {
                                        case bonding-connection {

                                            leaf bonding-connection {
                                                type types-submgt:bonding-connection-index;
                                                description "Connection ID over which packet is forwarded";
                                            }

                                        }
                                        case esi-l2 {
                                            status obsolete;

                                            container esi-l2 {
                                                status obsolete;
                                                presence "Enable the esi-l2 context";
                                                description "Enable the esi-l2 context";

                                                leaf esi-value {
                                                    status obsolete;
                                                    type types-services:ethernet-segment-id {
                                                        pattern "(0x[0-9a-fA-F]{20})|([0-9a-fA-F]{2}(:[0-9a-fA-F]{2}){9})|([0-9a-fA-F]{2}(-[0-9a-fA-F]{2}){9})" {
                                                            error-message "'esi-value' must be 10-byte ESI hex (0x... or colon/hyphen octets)";
                                                        }
                                                    }
                                                    mandatory true;
                                                    description "ESI of the first ESI-identified appliance";
                                                }

                                                leaf vpls {
                                                    status obsolete;
                                                    type leafref {
                                                        path "../../../../../../../service/vpls/service-name";
                                                    }
                                                    mandatory true;
                                                    description "VPLS service name";
                                                }

                                            } // container esi-l2

                                        }
                                        case esi-l3 {
                                            status obsolete;

                                            container esi-l3 {
                                                status obsolete;
                                                presence "Enable the esi-l3 context";
                                                description "Enable the esi-l3 context";

                                                leaf sf-ip {
                                                    status obsolete;
                                                    type types-sros:ipv6-address;
                                                    sros-ext:immutable;
                                                    mandatory true;
                                                    description "IP address of the service function to forward traffic";
                                                }

                                                leaf esi-value {
                                                    status obsolete;
                                                    type types-services:ethernet-segment-id {
                                                        pattern "(0x[0-9a-fA-F]{20})|([0-9a-fA-F]{2}(:[0-9a-fA-F]{2}){9})|([0-9a-fA-F]{2}(-[0-9a-fA-F]{2}){9})" {
                                                            error-message "'esi-value' must be 10-byte ESI hex (0x... or colon/hyphen octets)";
                                                        }
                                                    }
                                                    sros-ext:immutable;
                                                    mandatory true;
                                                    description "ESI of the first ESI-identified appliance";
                                                }

                                                leaf vas-interface {
                                                    status obsolete;
                                                    type leafref {
                                                        path "../../../../../../../service/vprn[service-name=current()/../vprn]/interface/interface-name";
                                                    }
                                                    sros-ext:immutable;
                                                    mandatory true;
                                                    description "Egress R-VPLS IP interface name";
                                                }

                                                leaf vprn {
                                                    status obsolete;
                                                    type leafref {
                                                        path "../../../../../../../service/vprn/service-name";
                                                    }
                                                    sros-ext:immutable;
                                                    mandatory true;
                                                    description "VPRN service name";
                                                }

                                            } // container esi-l3

                                        }
                                        case router {

                                            leaf router-instance {
                                                type string;
                                                sros-ext:immutable;
                                                description "Router name or VPRN service name";
                                            }

                                        }
                                        case next-hop {

                                            container next-hop {
                                                presence "Enable the next-hop context";
                                                description "Enable the next-hop context";

                                                choice next-hop {
                                                    mandatory true;
                                                    case nh-ip {

                                                        container nh-ip {
                                                            presence "Enable the nh-ip context";
                                                            description "Enable the nh-ip context";

                                                            leaf indirect {
                                                                type boolean;
                                                                default "false";
                                                                description "Allow next hop to be indirectly reachable";
                                                            }

                                                            leaf address {
                                                                type types-sros:ipv6-address;
                                                                mandatory true;
                                                                description "IPv6 address of next hop to forward matching packets";
                                                            }

                                                        } // container nh-ip

                                                    }
                                                    case nh-ip-vrf {

                                                        container nh-ip-vrf {
                                                            presence "Enable the nh-ip-vrf context";
                                                            description "Enable the nh-ip-vrf context";

                                                            leaf indirect {
                                                                type boolean;
                                                                default "false";
                                                                description "Allow next hop to be indirectly reachable";
                                                            }

                                                            leaf router-instance {
                                                                type string;
                                                                sros-ext:immutable;
                                                                mandatory true;
                                                                description "Routing context for route lookup for forwarding packets";
                                                            }

                                                            leaf address {
                                                                type types-sros:ipv6-address;
                                                                mandatory true;
                                                                description "IPv6 address of next hop to forward matching packets";
                                                            }

                                                        } // container nh-ip-vrf

                                                    }
                                                }
                                            } // container next-hop

                                        }
                                        case lsp {

                                            leaf lsp {
                                                type types-sros:named-item-64;
                                                description "LSP that is specified to forward a packet matching this entry";
                                            }

                                        }
                                        case lsp-container {

                                            leaf lsp-container {
                                                type leafref {
                                                    path "../../../../../../router/mpls/lsp-container/container-name";
                                                }
                                                description "LSP container whose members forward matching packets";
                                            }

                                        }
                                        case sdp {

                                            container sdp {
                                                presence "Enable the sdp context";
                                                description "Enable the sdp context";

                                                leaf vpls {
                                                    type leafref {
                                                        path "../../../../../../../service/vpls/service-name";
                                                    }
                                                    mandatory true;
                                                    description "VPLS associated with the SDP";
                                                }

                                                leaf sdp-bind-id {
                                                    type types-services:sdp-bind-id;
                                                    mandatory true;
                                                    description "VPLS SDP bind ID used to forward matching packets";
                                                }

                                            } // container sdp

                                        }
                                        case sap {

                                            container sap {
                                                presence "Enable the sap context";
                                                description "Enable the sap context";

                                                leaf vpls {
                                                    type leafref {
                                                        path "../../../../../../../service/vpls/service-name";
                                                    }
                                                    mandatory true;
                                                    description "VPLS associated with the SAP";
                                                }

                                                leaf sap-id {
                                                    type leafref {
                                                        path "../../../../../../../service/vpls[service-name=current()/../vpls]/sap/sap-id";
                                                    }
                                                    mandatory true;
                                                    description "VPLS Ethernet SAP ID used to forward matching packets";
                                                }

                                            } // container sap

                                        }
                                        case redirect-policy {

                                            leaf redirect-policy {
                                                type leafref {
                                                    path "../../../../../redirect-policy/redirect-policy-name";
                                                }
                                                sros-ext:immutable;
                                                description "Next hop or forward next hop router that forwards a packet that matches this entry";
                                            }

                                        }
                                        case vprn-target {

                                            container vprn-target {
                                                presence "Enable the vprn-target context";
                                                description "Enable the vprn-target context";

                                                leaf bgp-nh {
                                                    type types-sros:ipv4-address {
                                                        pattern "((([0-9]|[1-9][0-9]|1[0-9][0-9]|2[0-4][0-9]|25[0-5])\\.){3}([1-9]|[1-9][0-9]|1[0-9][0-9]|2[0-4][0-9]|25[0-5]))|
                                                                         ((([0-9]|[1-9][0-9]|1[0-9][0-9]|2[0-4][0-9]|25[0-5])\\.){2}(([1-9]|[1-9][0-9]|1[0-9][0-9]|2[0-4][0-9]|25[0-5])\\.){1}([0-9]|[1-9][0-9]|1[0-9][0-9]|2[0-4][0-9]|25[0-5]){1})|
                                                                         ((([0-9]|[1-9][0-9]|1[0-9][0-9]|2[0-4][0-9]|25[0-5])\\.){1}([1-9]|[1-9][0-9]|1[0-9][0-9]|2[0-4][0-9]|25[0-5]){1}(\\.([0-9]|[1-9][0-9]|1[0-9][0-9]|2[0-4][0-9]|25[0-5])){2})|
                                                                         (([1-9]|[1-9][0-9]|1[0-9][0-9]|2[0-4][0-9]|25[0-5]){1}(\\.([0-9]|[1-9][0-9]|1[0-9][0-9]|2[0-4][0-9]|25[0-5])){3})" {
                                                            error-message "'bgp-nh' must be IPv4 unicast (non-zero) in dotted notation";
                                                        }
                                                    }
                                                    mandatory true;
                                                    description "Target BGP next hop IP address";
                                                }

                                                leaf vprn {
                                                    type leafref {
                                                        path "../../../../../../../service/vprn/service-name";
                                                    }
                                                    mandatory true;
                                                    description "Routing context used for route lookup";
                                                }

                                                leaf lsp {
                                                    type types-sros:named-item-64;
                                                    description "LSP that is specified to forward a packet matching this entry";
                                                }

                                                leaf adv-prefix {
                                                    type types-sros:ipv6-prefix;
                                                    description "Advertised IP prefix for target destination";
                                                }

                                            } // container vprn-target

                                        }
                                        case gre-tunnel {

                                            leaf gre-tunnel {
                                                type leafref {
                                                    path "../../../../../gre-tunnel-template/gre-tunnel-template-name";
                                                }
                                                description "GRE tunnel template ID that sets the location where an encapsulated matching packet is transported";
                                            }

                                        }
                                        case mpls-policy {

                                            container mpls-policy {
                                                presence "Enable the mpls-policy context";
                                                description "Enable the mpls-policy context";

                                                leaf endpoint {
                                                    type types-sros:ipv6-unicast-address;
                                                    mandatory true;
                                                    description "MPLS forwarding policy endpoint IPv6 address";
                                                }

                                            } // container mpls-policy

                                        }
                                        case srte-policy {

                                            container srte-policy {
                                                presence "Enable the srte-policy context";
                                                description "Enable the srte-policy context";

                                                leaf endpoint {
                                                    type types-sros:ipv6-unicast-or-zero-address;
                                                    mandatory true;
                                                    description "SR-TE policy endpoint IPv6 address";
                                                }

                                                leaf color {
                                                    type int64 {
                                                        range "0..4294967295";
                                                    }
                                                    mandatory true;
                                                    description "SR-TE policy color ID";
                                                }

                                            } // container srte-policy

                                        }
                                        case srv6-policy {

                                            container srv6-policy {
                                                presence "Enable the srv6-policy context";
                                                description "Enable the srv6-policy context";

                                                leaf endpoint {
                                                    type types-sros:ipv6-unicast-or-zero-address;
                                                    mandatory true;
                                                    description "SRv6 policy endpoint IPv6 address";
                                                }

                                                leaf color {
                                                    type uint32 {
                                                        range "0..4294967295";
                                                    }
                                                    mandatory true;
                                                    description "SRv6 policy color";
                                                }

                                                leaf service-sid {
                                                    type types-sros:ipv6-unicast-address;
                                                    mandatory true;
                                                    description "SRv6 service segment identifier";
                                                }

                                            } // container srv6-policy

                                        }
                                    }
                                } // container forward

                            }
                            case http-redirect {

                                container http-redirect {
                                    presence "Enable the http-redirect context";
                                    description "Enable the http-redirect context";

                                    leaf url {
                                        type union {
                                            type enumeration {
                                                enum from-cpf                       { value 1; }
                                            }
                                            type types-sros:http-redirect-url;
                                        }
                                        sros-ext:immutable;
                                        mandatory true;
                                        description "URL used for HTTP redirect action";
                                    }

                                    leaf allow-override {
                                        type boolean;
                                        default "false";
                                        description "Override the HTTP redirect URL by a RADIUS VSA";
                                    }

                                } // container http-redirect

                            }
                            case nat {

                                container nat {
                                    presence "Enable the nat context";
                                    description "Enable the nat context";

                                    choice nat-choice {
                                        mandatory true;
                                        case nat-policy {

                                            leaf nat-type {
                                                type types-filter:nat-type;
                                                sros-ext:isa-auto-clear-on-modify;
                                                mandatory true;
                                                description "NAT type to assign when action is NAT";
                                            }

                                            leaf nat-policy {
                                                type leafref {
                                                    path "../../../../../../service/nat/nat-policy/name";
                                                }
                                                sros-ext:isa-auto-clear-on-modify;
                                                description "NAT policy name when action is NAT";
                                            }

                                        }
                                        case firewall-policy {

                                            leaf firewall-policy {
                                                type leafref {
                                                    path "../../../../../../service/nat/firewall-policy/name";
                                                }
                                                description "Firewall policy associated with a filter entry";
                                            }

                                        }
                                    }
                                } // container nat

                            }
                            case reassemble {

                                leaf reassemble {
                                    type empty;
                                    description "A packet matching the ipv6-filter entry will be forwarded to the packet REASSEMBLE function in the system.";
                                }

                            }
                            case tcp-mss-adjust {

                                leaf tcp-mss-adjust {
                                    type empty;
                                    description "Adjust MSS option of TCP matching packets to configured value of tcp-mss in router interface context";
                                }

                            }
                            case accept {

                                leaf accept {
                                    type empty;
                                    description "Accept regular routing to forward a matching packet";
                                }

                            }
                        }
                        container remark {
                            presence "Enable the remark context";
                            description "Enable the remark context";

                            leaf dscp {
                                type types-qos:dscp-name;
                                mandatory true;
                                description "Destination SAP";
                            }

                        } // container remark

                        container rate-limit {
                            presence "Enable the rate-limit context";
                            description "Enable the rate-limit context";

                            leaf mbs {
                                type union {
                                    type uint32 {
                                        range "0..268435456";
                                    }
                                    type enumeration {
                                        enum auto                           { value -1; }
                                    }
                                }
                                units "bytes";
                                default "auto";
                                description "Maximum burst size";
                            }

                            choice pir-choice {
                                mandatory true;
                                case pir-case {

                                    leaf pir {
                                        type types-filter:rate-limit-pir-kilobps;
                                        units "kilobps";
                                        description "Peak information rate";
                                    }

                                }
                                case pps-pir-case {

                                    leaf pps-pir {
                                        type types-filter:rate-limit-pir-pps;
                                        units "packets per second";
                                        description "Peak information rate";
                                    }

                                }
                                case policer-case {

                                    leaf policer {
                                        type types-sros:named-item;
                                        description "Policer name to use for rate limiting traffic";
                                    }

                                }
                            }
                            choice criterion-1 {
                                case hop-limit {

                                    container hop-limit {
                                        presence "Enable the hop-limit context";
                                        description "Enable the hop-limit context";

                                        choice hop-limit {
                                            mandatory true;
                                            case eq {

                                                leaf eq {
                                                    type types-filter:ttl-or-hop-limit-value;
                                                    description "Equal to condition match value";
                                                }

                                            }
                                            case lt {

                                                leaf lt {
                                                    type types-filter:ttl-or-hop-limit-lt-value;
                                                    description "Less than condition match value";
                                                }

                                            }
                                            case gt {

                                                leaf gt {
                                                    type types-filter:ttl-or-hop-limit-gt-value;
                                                    description "Greater than condition match value";
                                                }

                                            }
                                            case range {

                                                container range {
                                                    presence "Enable the range context";
                                                    description "Enable the range context";

                                                    leaf start {
                                                        type types-filter:ttl-or-hop-limit-gt-value;
                                                        mandatory true;
                                                        description "Lower bound of the range";
                                                    }

                                                    leaf end {
                                                        type types-filter:ttl-or-hop-limit-lt-value;
                                                        mandatory true;
                                                        description "Upper bound of the range";
                                                    }

                                                } // container range

                                            }
                                        }
                                    } // container hop-limit

                                }
                                case payload-length {

                                    container payload-length {
                                        presence "Enable the payload-length context";
                                        description "Enable the payload-length context";

                                        choice payload-length {
                                            mandatory true;
                                            case eq {

                                                leaf eq {
                                                    type types-filter:pkt-len-or-payload-len-value;
                                                    description "Exact match criterion for the length";
                                                }

                                            }
                                            case lt {

                                                leaf lt {
                                                    type types-filter:pkt-len-or-payload-len-lt-value;
                                                    description "Less than match criterion for the length";
                                                }

                                            }
                                            case gt {

                                                leaf gt {
                                                    type types-filter:pkt-len-or-payload-len-gt-value;
                                                    description "Greater than match criterion for the length";
                                                }

                                            }
                                            case range {

                                                container range {
                                                    presence "Enable the range context";
                                                    description "Enable the range context";

                                                    leaf start {
                                                        type types-filter:pkt-len-or-payload-len-gt-value;
                                                        mandatory true;
                                                        description "Lower bound of the length range";
                                                    }

                                                    leaf end {
                                                        type types-filter:pkt-len-or-payload-len-lt-value;
                                                        mandatory true;
                                                        description "Upper bound of the length range";
                                                    }

                                                } // container range

                                            }
                                        }
                                    } // container payload-length

                                }
                            }
                            choice choice2 {
                                case extracted-traffic-case {

                                    leaf extracted-traffic {
                                        type empty;
                                        description "Limit the rate of traffic extracted to the CPM";
                                    }

                                }
                            }
                            container pattern {
                                presence "Enable the pattern context";
                                description "Enable the pattern context";

                                leaf expression {
                                    type types-sros:hex-string {
                                        length "3..18";
                                    }
                                    mandatory true;
                                    description "Pattern expression to match";
                                }

                                leaf mask {
                                    type types-sros:hex-string {
                                        length "3..18";
                                        pattern "0x[a-fA-F0-9]*[a-fA-F1-9]+[a-fA-F0-9]*" {
                                            error-message "'mask' must be 0x-prefixed hex and not all zeros (e.g. 0x1a2b)";
                                        }
                                    }
                                    mandatory true;
                                    description "Mask for the pattern expression";
                                }

                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                leaf offset-value {
                                    type int32 {
                                        range "0..255";
                                    }
                                    mandatory true;
                                    description "Offset value for the pattern expression";
                                }

                            } // container pattern

                        } // container rate-limit

                        container drop-when {
                            presence "Enable the drop-when context";
                            description "Enable the drop-when context";

                            choice criterion-1 {
                                case hop-limit {

                                    container hop-limit {
                                        presence "Enable the hop-limit context";
                                        description "Enable the hop-limit context";

                                        choice hop-limit {
                                            mandatory true;
                                            case eq {

                                                leaf eq {
                                                    type types-filter:ttl-or-hop-limit-value;
                                                    description "Equal to condition match value";
                                                }

                                            }
                                            case lt {

                                                leaf lt {
                                                    type types-filter:ttl-or-hop-limit-lt-value;
                                                    description "Less than condition match value";
                                                }

                                            }
                                            case gt {

                                                leaf gt {
                                                    type types-filter:ttl-or-hop-limit-gt-value;
                                                    description "Greater than condition match value";
                                                }

                                            }
                                            case range {

                                                container range {
                                                    presence "Enable the range context";
                                                    description "Enable the range context";

                                                    leaf start {
                                                        type types-filter:ttl-or-hop-limit-gt-value;
                                                        mandatory true;
                                                        description "Lower bound of the range";
                                                    }

                                                    leaf end {
                                                        type types-filter:ttl-or-hop-limit-lt-value;
                                                        mandatory true;
                                                        description "Upper bound of the range";
                                                    }

                                                } // container range

                                            }
                                        }
                                    } // container hop-limit

                                }
                                case payload-length {

                                    container payload-length {
                                        presence "Enable the payload-length context";
                                        description "Enable the payload-length context";

                                        choice payload-length {
                                            mandatory true;
                                            case eq {

                                                leaf eq {
                                                    type types-filter:pkt-len-or-payload-len-value;
                                                    description "Exact match criterion for the length";
                                                }

                                            }
                                            case lt {

                                                leaf lt {
                                                    type types-filter:pkt-len-or-payload-len-lt-value;
                                                    description "Less than match criterion for the length";
                                                }

                                            }
                                            case gt {

                                                leaf gt {
                                                    type types-filter:pkt-len-or-payload-len-gt-value;
                                                    description "Greater than match criterion for the length";
                                                }

                                            }
                                            case range {

                                                container range {
                                                    presence "Enable the range context";
                                                    description "Enable the range context";

                                                    leaf start {
                                                        type types-filter:pkt-len-or-payload-len-gt-value;
                                                        mandatory true;
                                                        description "Lower bound of the length range";
                                                    }

                                                    leaf end {
                                                        type types-filter:pkt-len-or-payload-len-lt-value;
                                                        mandatory true;
                                                        description "Upper bound of the length range";
                                                    }

                                                } // container range

                                            }
                                        }
                                    } // container payload-length

                                }
                            }
                            choice criterion-2 {
                                case extracted-traffic {

                                    leaf extracted-traffic {
                                        type empty;
                                        description "Drop traffic extracted to CPM";
                                    }

                                }
                            }
                            container pattern {
                                presence "Enable the pattern context";
                                description "Enable the pattern context";

                                leaf expression {
                                    type types-sros:hex-string {
                                        length "3..18";
                                    }
                                    mandatory true;
                                    description "Pattern expression to match";
                                }

                                leaf mask {
                                    type types-sros:hex-string {
                                        length "3..18";
                                        pattern "0x[a-fA-F0-9]*[a-fA-F1-9]+[a-fA-F0-9]*" {
                                            error-message "'mask' must be 0x-prefixed hex and not all zeros (e.g. 0x1a2b)";
                                        }
                                    }
                                    mandatory true;
                                    description "Mask for the pattern expression";
                                }

                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                leaf offset-value {
                                    type int32 {
                                        range "0..255";
                                    }
                                    mandatory true;
                                    description "Offset value for the pattern expression";
                                }

                            } // container pattern

                        } // container drop-when

                        container accept-when {
                            presence "Enable the accept-when context";
                            description "Enable the accept-when context";

                            container pattern {
                                presence "Enable the pattern context";
                                description "Enable the pattern context";

                                leaf expression {
                                    type types-sros:hex-string {
                                        length "3..18";
                                    }
                                    mandatory true;
                                    description "Pattern expression to match";
                                }

                                leaf mask {
                                    type types-sros:hex-string {
                                        length "3..18";
                                        pattern "0x[a-fA-F0-9]*[a-fA-F1-9]+[a-fA-F0-9]*" {
                                            error-message "'mask' must be 0x-prefixed hex and not all zeros (e.g. 0x1a2b)";
                                        }
                                    }
                                    mandatory true;
                                    description "Mask for the pattern expression";
                                }

                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                leaf offset-value {
                                    type int32 {
                                        range "0..255";
                                    }
                                    mandatory true;
                                    description "Offset value for the pattern expression";
                                }

                            } // container pattern

                        } // container accept-when

                        container secondary {
                            presence "Enable the secondary context";
                            description "Enable the secondary context";

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice action {
                                mandatory true;
                                case forward {

                                    container forward {
                                        description "Enter the forward context";

                                        choice forward-action {
                                            case next-hop {

                                                container next-hop {
                                                    presence "Enable the next-hop context";
                                                    description "Enable the next-hop context";

                                                    choice next-hop {
                                                        mandatory true;
                                                        case nh-ip-vrf {

                                                            container nh-ip-vrf {
                                                                presence "Enable the nh-ip-vrf context";
                                                                description "Enable the nh-ip-vrf context";

                                                                leaf indirect {
                                                                    type boolean;
                                                                    default "false";
                                                                    description "Allow next hop to be indirectly reachable";
                                                                }

                                                                leaf router-instance {
                                                                    type string;
                                                                    sros-ext:immutable;
                                                                    mandatory true;
                                                                    description "Routing context for route lookup for forwarding packets";
                                                                }

                                                                leaf address {
                                                                    type types-sros:ipv6-address;
                                                                    mandatory true;
                                                                    description "IPv6 address of next hop to forward matching packets";
                                                                }

                                                            } // container nh-ip-vrf

                                                        }
                                                    }
                                                } // container next-hop

                                            }
                                            case sdp {

                                                container sdp {
                                                    presence "Enable the sdp context";
                                                    description "Enable the sdp context";

                                                    leaf vpls {
                                                        type leafref {
                                                            path "../../../../../../../../service/vpls/service-name";
                                                        }
                                                        mandatory true;
                                                        description "VPLS associated with the SDP";
                                                    }

                                                    leaf sdp-bind-id {
                                                        type types-services:sdp-bind-id;
                                                        sros-ext:immutable;
                                                        mandatory true;
                                                        description "VPLS SDP bind ID used to forward matching packets";
                                                    }

                                                } // container sdp

                                            }
                                            case sap {

                                                container sap {
                                                    presence "Enable the sap context";
                                                    description "Enable the sap context";

                                                    leaf vpls {
                                                        type leafref {
                                                            path "../../../../../../../../service/vpls/service-name";
                                                        }
                                                        mandatory true;
                                                        description "VPLS the sdp-bind-id belongs to";
                                                    }

                                                    leaf sap-id {
                                                        type leafref {
                                                            path "../../../../../../../../service/vpls[service-name=current()/../vpls]/sap/sap-id";
                                                        }
                                                        sros-ext:immutable;
                                                        mandatory true;
                                                        description "SAP ID used to forward packets matching the entry";
                                                    }

                                                } // container sap

                                            }
                                            case vprn-target {

                                                container vprn-target {
                                                    presence "Enable the vprn-target context";
                                                    description "Enable the vprn-target context";

                                                    leaf bgp-nh {
                                                        type types-sros:ipv4-address {
                                                            pattern "((([0-9]|[1-9][0-9]|1[0-9][0-9]|2[0-4][0-9]|25[0-5])\\.){3}([1-9]|[1-9][0-9]|1[0-9][0-9]|2[0-4][0-9]|25[0-5]))|
                                                                             ((([0-9]|[1-9][0-9]|1[0-9][0-9]|2[0-4][0-9]|25[0-5])\\.){2}(([1-9]|[1-9][0-9]|1[0-9][0-9]|2[0-4][0-9]|25[0-5])\\.){1}([0-9]|[1-9][0-9]|1[0-9][0-9]|2[0-4][0-9]|25[0-5]){1})|
                                                                             ((([0-9]|[1-9][0-9]|1[0-9][0-9]|2[0-4][0-9]|25[0-5])\\.){1}([1-9]|[1-9][0-9]|1[0-9][0-9]|2[0-4][0-9]|25[0-5]){1}(\\.([0-9]|[1-9][0-9]|1[0-9][0-9]|2[0-4][0-9]|25[0-5])){2})|
                                                                             (([1-9]|[1-9][0-9]|1[0-9][0-9]|2[0-4][0-9]|25[0-5]){1}(\\.([0-9]|[1-9][0-9]|1[0-9][0-9]|2[0-4][0-9]|25[0-5])){3})" {
                                                                error-message "'bgp-nh' must be IPv4 unicast (non-zero) in dotted notation";
                                                            }
                                                        }
                                                        mandatory true;
                                                        description "Target BGP next hop IP address";
                                                    }

                                                    leaf vprn {
                                                        type leafref {
                                                            path "../../../../../../../../service/vprn/service-name";
                                                        }
                                                        mandatory true;
                                                        description "Routing context used for route lookup";
                                                    }

                                                    leaf lsp {
                                                        type types-sros:named-item-64;
                                                        description "LSP that is specified to forward a packet matching this entry";
                                                    }

                                                    leaf adv-prefix {
                                                        type types-sros:ipv6-prefix;
                                                        description "Advertised IP prefix for the target destination";
                                                    }

                                                } // container vprn-target

                                            }
                                        }
                                    } // container forward

                                }
                            }
                            container remark {
                                presence "Enable the remark context";
                                description "Enable the remark context";

                                leaf dscp {
                                    type types-qos:dscp-name;
                                    mandatory true;
                                    description "Destination SAP";
                                }

                            } // container remark

                        } // container secondary

                    } // container action

                } // list entry

                container embed {
                    description "Enter the embed context";

                    list filter {
                        key "name offset";
                        description "Enter the filter list instance";

                        leaf name {
                            type leafref {
                                path "../../../../ipv6-filter/filter-name";
                            }
                            description "IPv6 policy to be embedded in the filter";
                        }

                        leaf offset {
                            type types-filter:embed-offset {
                                range "0..2097150";
                            }
                            description "Offset of the embedded filter policy";
                        }

                        leaf admin-state {
                            type types-sros:admin-state;
                            default "enable";
                            description "Administrative state of the embedded filter";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list filter

                    list flowspec {
                        key "offset";
                        description "Enter the flowspec list instance";

                        leaf offset {
                            type types-filter:embed-offset;
                            description "Offset of the inserted entries";
                        }

                        leaf group {
                            type uint32 {
                                range "0..16383";
                            }
                            sros-ext:immutable;
                            description "Group ID of FlowSpec routes to embed in the filter";
                        }

                        leaf router-instance {
                            type string;
                            sros-ext:immutable;
                            mandatory true;
                            description "Routing instance source of BGP FlowSpec routes";
                        }

                        leaf admin-state {
                            type types-sros:admin-state;
                            default "enable";
                            description "Administrative state of the embedded filter";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list flowspec

                    list openflow {
                        status obsolete;
                        key "of-switch offset";
                        description "Enter the openflow list instance";

                        leaf of-switch {
                            status obsolete;
                            type types-sros:named-item;
                            description "Referenced Hybrid OpenFlow Switch (OFS) name";
                        }

                        leaf offset {
                            status obsolete;
                            type types-filter:embed-offset {
                                range "0..2097150";
                            }
                            description "Offset of the embedded filter policy";
                        }

                        leaf admin-state {
                            status obsolete;
                            type types-sros:admin-state;
                            default "enable";
                            description "Administrative state of the embedded filter";
                        }

                        leaf-list apply-groups {
                            status obsolete;
                            type leafref {
                                path "../../../../../groups/group/name";
                            }
                            max-elements 8;
                            ordered-by user;
                            description "Apply a configuration group at this level";
                        }

                        leaf-list apply-groups-exclude {
                            status obsolete;
                            type leafref {
                                path "../../../../../groups/group/name";
                            }
                            max-elements 8;
                            ordered-by user;
                            description "Exclude a configuration group at this level";
                        }

                        choice context {
                            status obsolete;
                            default "grt";
                            description
                                "Specifies the context in which the openflow embedding is inserted into filter.
                                 When no context is present, this object is set to grt value.";
                            case grt {
                                status obsolete;

                                leaf grt {
                                    status obsolete;
                                    type empty;
                                    sros-ext:immutable;
                                    description "Global routing context";
                                }

                            }
                            case system {
                                status obsolete;

                                leaf system {
                                    status obsolete;
                                    type empty;
                                    sros-ext:immutable;
                                    description "System context";
                                }

                            }
                            case vprn {
                                status obsolete;

                                leaf vprn {
                                    status obsolete;
                                    type leafref {
                                        path "../../../../../service/vprn/service-name";
                                    }
                                    sros-ext:immutable;
                                    description "VPRN context";
                                }

                            }
                            case vpls {
                                status obsolete;

                                leaf vpls {
                                    status obsolete;
                                    type leafref {
                                        path "../../../../../service/vpls/service-name";
                                    }
                                    sros-ext:immutable;
                                    description "VPLS context";
                                }

                                leaf sap {
                                    status obsolete;
                                    type leafref {
                                        path "../../../../../service/vpls[service-name=current()/../vpls]/sap/sap-id";
                                    }
                                    sros-ext:immutable;
                                    description "SAP context";
                                }

                            }
                        }
                    } // list openflow

                } // container embed

            } // list ipv6-filter

            list mac-filter {
                key "filter-name";
                description "Enter the mac-filter list instance";

                leaf filter-name {
                    type types-filter:filter-name;
                    description "Filter name";
                }

                leaf default-action {
                    type types-filter:filter-default-action;
                    default "drop";
                    description "Action for packets that do not match any entry";
                }

                leaf description {
                    type types-sros:description;
                    description "Text description";
                }

                leaf scope {
                    type types-filter:filter-scope;
                    default "template";
                    description "Filter policy scope";
                }

                leaf type {
                    type types-qos:mac-filter-type;
                    sros-ext:immutable;
                    default "normal";
                    description "MAC filter policy";
                }

                leaf filter-id {
                    type types-filter:filter-id;
                    sros-ext:immutable;
                    description "MAC filter ID";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list entry {
                    key "entry-id";
                    description "Enter the entry list instance";

                    leaf entry-id {
                        type types-filter:entry-id;
                        description "ID for a match criteria and the corresponding action";
                    }

                    leaf description {
                        type types-sros:description;
                        description "Text description";
                    }

                    leaf pbr-down-action-override {
                        type types-filter:filter-pbr-down-action-ovr;
                        description "Action when PBR or PBF target for this entry is not available";
                    }

                    leaf sticky-dest {
                        type types-filter:filter-sticky-dest;
                        units "seconds";
                        description "Time before action with available PBR or PBF destination and highest priority";
                    }

                    leaf log {
                        type leafref {
                            path "../../../log/log-id";
                        }
                        description "Log that is used for packets matching this entry";
                    }

                    leaf collect-stats {
                        type boolean;
                        default "false";
                        description "Enable statistics collection for an entry";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container match {
                        description "Enter the match context";

                        leaf frame-type {
                            type types-filter:mac-frame-type;
                            description "MAC frame as match criteria";
                        }

                        leaf etype {
                            type types-services:etype-value;
                            description "Ethernet type";
                        }

                        leaf snap-pid {
                            type int32 {
                                range "0..65535";
                            }
                            description "Parameter snap-pid as a MAC filter match criteria";
                        }

                        leaf snap-oui {
                            type enumeration {
                                enum zero                           { value 2; }
                                enum non-zero                       { value 3; }
                            }
                            description "Parameter snap-oui as a MAC filter match criteria";
                        }

                        container src-mac {
                            presence "Enable the src-mac context";
                            description "Enable the src-mac context";

                            leaf address {
                                type yang:mac-address;
                                mandatory true;
                                description "MAC address used as the match criterion";
                            }

                            leaf mask {
                                type yang:mac-address;
                                default "ff:ff:ff:ff:ff:ff";
                                description "MAC address mask as the match criterion";
                            }

                        } // container src-mac

                        container dst-mac {
                            presence "Enable the dst-mac context";
                            description "Enable the dst-mac context";

                            leaf address {
                                type yang:mac-address;
                                mandatory true;
                                description "MAC address used as the match criterion";
                            }

                            leaf mask {
                                type yang:mac-address;
                                default "ff:ff:ff:ff:ff:ff";
                                description "MAC address mask as the match criterion";
                            }

                        } // container dst-mac

                        container dot1p {
                            presence "Enable the dot1p context";
                            description "Enable the dot1p context";

                            leaf priority {
                                type types-qos:dot1p-priority;
                                mandatory true;
                                description "IEEE 802.1p value used as a MAC filter match criterion";
                            }

                            leaf mask {
                                type types-qos:dot1p-priority {
                                    range "1..7";
                                }
                                default "7";
                                description "802.1p mask value used as a MAC filter match criterion";
                            }

                        } // container dot1p

                        container llc-ssap {
                            presence "Enable the llc-ssap context";
                            description "Enable the llc-ssap context";

                            leaf ssap {
                                type types-qos:service-access-point;
                                mandatory true;
                                description "Source or destination SAP value";
                            }

                            leaf mask {
                                type types-qos:service-access-point {
                                    range "1..255";
                                }
                                default "255";
                                description "Source SAP mask";
                            }

                        } // container llc-ssap

                        container llc-dsap {
                            presence "Enable the llc-dsap context";
                            description "Enable the llc-dsap context";

                            leaf dsap {
                                type types-qos:service-access-point;
                                mandatory true;
                                description "DSAP value";
                            }

                            leaf mask {
                                type types-qos:service-access-point {
                                    range "1..255";
                                }
                                default "255";
                                description "Destination SAP mask";
                            }

                        } // container llc-dsap

                        container inner-tag {
                            presence "Enable the inner-tag context";
                            description "Enable the inner-tag context";

                            leaf tag {
                                type int32 {
                                    range "0..4095";
                                }
                                mandatory true;
                                description "Matching value against VID of the second or first VLAN tag in the packet carried transparently";
                            }

                            leaf mask {
                                type uint32 {
                                    range "1..4095";
                                }
                                default "4095";
                                description "Mask to VID of the inner VLAN tag before comparing it with the inner-tag or outer-tag value";
                            }

                        } // container inner-tag

                        container outer-tag {
                            presence "Enable the outer-tag context";
                            description "Enable the outer-tag context";

                            leaf tag {
                                type int32 {
                                    range "0..4095";
                                }
                                mandatory true;
                                description "Matching value against VID of the second or first VLAN tag in the packet carried transparently";
                            }

                            leaf mask {
                                type uint32 {
                                    range "1..4095";
                                }
                                default "4095";
                                description "Mask to VID of the inner VLAN tag before comparing it with the inner-tag or outer-tag value";
                            }

                        } // container outer-tag

                        container isid {
                            description "Enter the isid context";

                            choice isid {
                                case isid-value {

                                    leaf value {
                                        type types-sros:svc-isid;
                                        description "Lowest value of 24-bit service instance identifier for the service matching this entry";
                                    }

                                }
                                case isid-range {

                                    container range {
                                        presence "Enable the range context";
                                        description "Enable the range context";

                                        leaf start {
                                            type types-sros:svc-isid;
                                            mandatory true;
                                            description "Lower bound of the ISID range";
                                        }

                                        leaf end {
                                            type types-sros:svc-isid;
                                            mandatory true;
                                            description "Upper bound of the ISID range";
                                        }

                                    } // container range

                                }
                            }
                        } // container isid

                    } // container match

                    container action {
                        presence "Enable the action context";
                        description "Enable the action context";

                        leaf fc {
                            type types-sros:fc-name;
                            description "Forwarding class for packets matching the entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice action {
                            mandatory true;
                            case ignore-match {

                                leaf ignore-match {
                                    type empty;
                                    description "Ignore match criteria for the entry";
                                }

                            }
                            case drop {

                                leaf drop {
                                    type empty;
                                    description "Drop a packet matching this entry";
                                }

                            }
                            case forward {

                                container forward {
                                    description "Enter the forward context";

                                    choice forward-action {
                                        case esi-l2 {
                                            status obsolete;

                                            container esi-l2 {
                                                status obsolete;
                                                presence "Enable the esi-l2 context";
                                                description "Enable the esi-l2 context";

                                                leaf esi-value {
                                                    status obsolete;
                                                    type types-services:ethernet-segment-id {
                                                        pattern "(0x[0-9a-fA-F]{20})|([0-9a-fA-F]{2}(:[0-9a-fA-F]{2}){9})|([0-9a-fA-F]{2}(-[0-9a-fA-F]{2}){9})" {
                                                            error-message "'esi-value' must be 10-byte ESI hex (0x... or colon/hyphen octets)";
                                                        }
                                                    }
                                                    mandatory true;
                                                    description "ESI of the first ESI-identified appliance";
                                                }

                                                leaf vpls {
                                                    status obsolete;
                                                    type leafref {
                                                        path "../../../../../../../service/vpls/service-name";
                                                    }
                                                    mandatory true;
                                                    description "VPLS service name";
                                                }

                                            } // container esi-l2

                                        }
                                        case sdp {

                                            container sdp {
                                                presence "Enable the sdp context";
                                                description "Enable the sdp context";

                                                leaf vpls {
                                                    type leafref {
                                                        path "../../../../../../../service/vpls/service-name";
                                                    }
                                                    mandatory true;
                                                    description "VPLS associated with the SDP";
                                                }

                                                leaf sdp-bind-id {
                                                    type types-services:sdp-bind-id;
                                                    mandatory true;
                                                    description "VPLS SDP bind ID used to forward matching packets";
                                                }

                                            } // container sdp

                                        }
                                        case sap {

                                            container sap {
                                                presence "Enable the sap context";
                                                description "Enable the sap context";

                                                leaf vpls {
                                                    type leafref {
                                                        path "../../../../../../../service/vpls/service-name";
                                                    }
                                                    mandatory true;
                                                    description "VPLS associated with the SAP";
                                                }

                                                leaf sap-id {
                                                    type leafref {
                                                        path "../../../../../../../service/vpls[service-name=current()/../vpls]/sap/sap-id";
                                                    }
                                                    mandatory true;
                                                    description "VPLS Ethernet SAP ID used to forward matching packets";
                                                }

                                            } // container sap

                                        }
                                    }
                                } // container forward

                            }
                            case http-redirect {

                                container http-redirect {
                                    presence "Enable the http-redirect context";
                                    description "Enable the http-redirect context";

                                    leaf url {
                                        type types-sros:http-redirect-url;
                                        sros-ext:immutable;
                                        mandatory true;
                                        description "URL that is used for redirecting";
                                    }

                                } // container http-redirect

                            }
                            case accept {

                                leaf accept {
                                    type empty;
                                    description "Accept regular routing to forward a matching packet";
                                }

                            }
                        }
                        container rate-limit {
                            presence "Enable the rate-limit context";
                            description "Enable the rate-limit context";

                            leaf pir {
                                type types-filter:rate-limit;
                                units "kilobps";
                                mandatory true;
                                description "Peak information rate";
                            }

                        } // container rate-limit

                        container secondary {
                            presence "Enable the secondary context";
                            description "Enable the secondary context";

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice action {
                                mandatory true;
                                case forward {

                                    container forward {
                                        description "Enter the forward context";

                                        choice forward-action {
                                            case sdp {

                                                container sdp {
                                                    presence "Enable the sdp context";
                                                    description "Enable the sdp context";

                                                    leaf vpls {
                                                        type leafref {
                                                            path "../../../../../../../../service/vpls/service-name";
                                                        }
                                                        mandatory true;
                                                        description "VPLS associated with the SDP";
                                                    }

                                                    leaf sdp-bind-id {
                                                        type types-services:sdp-bind-id;
                                                        sros-ext:immutable;
                                                        mandatory true;
                                                        description "VPLS SDP bind ID used to forward matching packets";
                                                    }

                                                } // container sdp

                                            }
                                            case sap {

                                                container sap {
                                                    presence "Enable the sap context";
                                                    description "Enable the sap context";

                                                    leaf vpls {
                                                        type leafref {
                                                            path "../../../../../../../../service/vpls/service-name";
                                                        }
                                                        mandatory true;
                                                        description "VPLS the sdp-bind-id belongs to";
                                                    }

                                                    leaf sap-id {
                                                        type leafref {
                                                            path "../../../../../../../../service/vpls[service-name=current()/../vpls]/sap/sap-id";
                                                        }
                                                        sros-ext:immutable;
                                                        mandatory true;
                                                        description "SAP ID used to forward packets matching the entry";
                                                    }

                                                } // container sap

                                            }
                                        }
                                    } // container forward

                                }
                            }
                        } // container secondary

                    } // container action

                } // list entry

                container embed {
                    description "Enter the embed context";

                } // container embed

            } // list mac-filter

            container system-filter {
                description "Enter the system-filter context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list ip {
                    key "ip-filter";
                    max-elements 1;
                    description "Add a list entry for ip";

                    leaf ip-filter {
                        type leafref {
                            path "../../../ip-filter/filter-name";
                        }
                        description "Active IPv4 system filter policy";
                    }

                } // list ip

                list ipv6 {
                    key "ipv6-filter";
                    max-elements 1;
                    description "Add a list entry for ipv6";

                    leaf ipv6-filter {
                        type leafref {
                            path "../../../ipv6-filter/filter-name";
                        }
                        description "Active IPv6 system filter policy";
                    }

                } // list ipv6

            } // container system-filter

            list gre-tunnel-template {
                key "gre-tunnel-template-name";
                max-elements 8191;
                description "Enter the gre-tunnel-template list instance";

                leaf gre-tunnel-template-name {
                    type types-sros:named-item;
                    description "GRE tunnel template ID";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice ipvx {
                    case ipv4 {

                        container ipv4 {
                            description "Enter the ipv4 context";

                            leaf source-address {
                                type types-sros:ipv4-address;
                                description "Source IP address of the GRE encapsulated";
                            }

                            leaf gre-key {
                                type types-filter:filter-gre-tunnel-gre-key;
                                description "GRE key";
                            }

                            leaf skip-ttl-decrement {
                                type boolean;
                                default "false";
                                description "Decrement TTL";
                            }

                            list destination-address {
                                key "address";
                                max-elements 32;
                                description "Add a list entry for destination-address";

                                leaf address {
                                    type types-sros:ipv4-address;
                                    description "Destination IPv4 address";
                                }

                            } // list destination-address

                        } // container ipv4

                    }
                    case ipv6 {

                        container ipv6 {
                            description "Enter the ipv6 context";

                            leaf source-address {
                                type types-sros:ipv6-unicast-address;
                                description "Source IPv6 address of the GRE encapsulated";
                            }

                            leaf gre-key {
                                type enumeration {
                                    enum if-index                       { value -2; }
                                }
                                description "Include a key value in GRE header";
                            }

                            leaf skip-hop-decrement {
                                type boolean;
                                default "false";
                                description "Decrement TTL of the received packet";
                            }

                            list destination-address {
                                key "address";
                                max-elements 1;
                                description "Add a list entry for destination-address";

                                leaf address {
                                    type types-sros:ipv6-unicast-address;
                                    description "IPv6 destination address";
                                }

                            } // list destination-address

                        } // container ipv6

                    }
                }
            } // list gre-tunnel-template

            list filter-set {
                key "filter-set-name";
                max-elements 16384;
                description "Enter the filter-set list instance";

                leaf filter-set-name {
                    type string {
                        length "1..32";
                        pattern "(.*\\S.*)|()" {
                            error-message "'filter-set-name' must contain at least one non-space character";
                        }
                    }
                    description "Filter-set name";
                }

                leaf description {
                    type types-sros:description;
                    description "Text description";
                }

                leaf mac-filter {
                    type leafref {
                        path "../../mac-filter/filter-name";
                    }
                    description "MAC filter ID";
                }

                leaf ip-filter {
                    type leafref {
                        path "../../ip-filter/filter-name";
                    }
                    description "IPv4 filter ID";
                }

                leaf ipv6-filter {
                    type leafref {
                        path "../../ipv6-filter/filter-name";
                    }
                    description "IPv6 filter ID";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list filter-set

            container md-auto-id {
                description "Enter the md-auto-id context";

                container filter-id-range {
                    presence "Enable the filter-id-range context";
                    description "Enable the filter-id-range context";

                    leaf start {
                        type types-filter:filter-id;
                        sros-ext:immutable;
                        mandatory true;
                        description "Lower bound of the ID range";
                    }

                    leaf end {
                        type types-filter:filter-id;
                        sros-ext:immutable;
                        mandatory true;
                        description "Upper bound of the ID range";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container filter-id-range

            } // container md-auto-id

            list policer {
                key "policer-name";
                max-elements 8192;
                description "Enter the policer list instance";

                leaf policer-name {
                    type types-sros:named-item;
                    description "Name of the policer for use in a filter policy";
                }

                leaf description {
                    type types-sros:description;
                    description "Text description";
                }

                leaf scope {
                    type enumeration {
                        enum filter {
                            value 0;
                            description "Policer shared by entries in same filter policer";
                        }
                        enum system {
                            value 1;
                            description "Single policer shared by the system";
                        }
                    }
                    sros-ext:immutable;
                    default "filter";
                    description "Policer scope";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice pir-choice {
                    default "pir-case";
                    case pir-case {

                        leaf pir {
                            type int32 {
                                range "0..2000000000";
                            }
                            units "kilobps";
                            description "Peak information rate";
                        }

                        leaf mbs {
                            type union {
                                type uint32 {
                                    range "0..268435456";
                                }
                                type enumeration {
                                    enum auto                           { value -1; }
                                }
                            }
                            units "bytes";
                            default "auto";
                            description "Maximum burst size";
                        }

                    }
                    case pps-pir-case {

                        leaf pps-pir {
                            type int32 {
                                range "0..100000000";
                            }
                            units "packets per second";
                            description "Peak information rate";
                        }

                    }
                }
            } // list policer

            uses conf-filter-dhcp-dhcp-filter;
            uses conf-filter-dhcp-dhcp6-filter;
            uses conf-filter-ip-exception;
            uses conf-filter-ip-exception-ipv6-exception;
        } // container filter

    } // grouping conf-filter

}
