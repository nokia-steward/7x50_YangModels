submodule nokia-conf-port-dwdm-coherent {

    yang-version "1.1";

    belongs-to nokia-conf { prefix "conf"; }

    import nokia-sros-yang-extensions     { prefix "sros-ext"; }
    import nokia-types-port               { prefix "types-port"; }

    include nokia-conf-groups;

    sros-ext:sros-major-release "rel26";
    organization "Nokia";
    contact
        "Nokia SR OS Support
         Web: <http://www.nokia.com>";
    description
        "Nokia YANG Data model to configure dense wavelength division multiplexing coherent ports on SR OS based routers.

         Copyright 2016 Nokia. All rights reserved. Reproduction of this document
         is authorized on the condition that the foregoing copyright notice is included.

         This nokia-conf-port-dwdm-coherent YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping conf-port-dwdm-coherent {
        container coherent {
            description "Enter the coherent context";

            leaf channel {
                status obsolete;
                type types-port:optical-dwdm-channel;
                description "DWDM ITU channel number";
            }

            leaf compatibility {
                type types-port:optical-compatibility-mode;
                default "long-haul";
                description "Optical mode and rate of operation";
            }

            leaf cpr-window-size {
                type uint32 {
                    range "2|4|8|16|32|64";
                }
                units "symbols";
                description "Window size for the carrier phase recovery";
            }

            leaf dispersion {
                type int32 {
                    range "-50000..50000";
                }
                units "picoseconds per nanometer";
                description "Residual chromatic dispersion compensation";
            }

            leaf mode {
                type types-port:optical-dispersion-control-mode;
                default "automatic";
                description "Mode used to compensate for chromatic dispersion";
            }

            leaf operational-mode {
                type types-port:optical-operational-mode;
                description "Coherent optic operational mode";
            }

            leaf rx-los-reaction {
                type types-port:los-reaction;
                default "squelch";
                description "Reaction to an RX LOS";
            }

            leaf rx-los-thresh {
                type decimal64 {
                    range "-30..-13";
                    fraction-digits 2;
                }
                units "decibel-milliwatts";
                default "-23";
                description "Average input power LOS threshold";
            }

            leaf target-power {
                type decimal64 {
                    range "-20..3";
                    fraction-digits 2;
                }
                units "decibel-milliwatts";
                default "1";
                description "Average output power target for the port";
            }

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            container report-alarm {
                description "Enter the report-alarm context";

                leaf modflt {
                    type boolean;
                    default "true";
                    description "Report the module fault alarm";
                }

                leaf mod {
                    type boolean;
                    default "true";
                    description "Report the module alarm";
                }

                leaf netrx {
                    type boolean;
                    default "true";
                    description "Report the network (optical side) receive alarm";
                }

                leaf nettx {
                    type boolean;
                    default "true";
                    description "Report the network (optical side) transmit alarm";
                }

                leaf hosttx {
                    type boolean;
                    default "true";
                    description "Report the host (electrical side) transmit alarm";
                }

                leaf cfg {
                    type boolean;
                    description "Enable/disable cfg alarm.";
                }

            } // container report-alarm

            container sweep {
                description "Enter the sweep context";

                leaf start {
                    type int32 {
                        range "-50000..50000";
                    }
                    units "picoseconds per nanometer";
                    default "-25500";
                    description "Lower bound of the dispersion compensation range";
                }

                leaf end {
                    type int32 {
                        range "-50000..50000";
                    }
                    units "picoseconds per nanometer";
                    default "2000";
                    description "Upper bound of the dispersion compensation range";
                }

            } // container sweep

        } // container coherent

    } // grouping conf-port-dwdm-coherent

}
