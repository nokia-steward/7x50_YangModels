submodule nokia-conf-saa {

    yang-version "1.1";

    belongs-to nokia-conf { prefix "conf"; }

    import nokia-sros-yang-extensions     { prefix "sros-ext"; }
    import nokia-types-eth-cfm            { prefix "types-eth-cfm"; }
    import nokia-types-oam                { prefix "types-oam"; }
    import nokia-types-qos                { prefix "types-qos"; }
    import nokia-types-services           { prefix "types-services"; }
    import nokia-types-sros               { prefix "types-sros"; }

    include nokia-conf-groups;
    include nokia-conf-log;

    sros-ext:sros-major-release "rel26";
    organization "Nokia";
    contact
        "Nokia SR OS Support
         Web: <http://www.nokia.com>";
    description
        "Nokia YANG Data model to configure Service Assurance Agent (SAA) on SR OS based routers.

         Copyright 2016 Nokia. All rights reserved. Reproduction of this document
         is authorized on the condition that the foregoing copyright notice is included.

         This nokia-conf-saa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-10-28";

    grouping conf-saa {
        container saa {
            description "Enter the saa context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list owner {
                key "owner-name test";
                description "Enter the owner list instance";

                leaf owner-name {
                    type types-sros:named-item;
                    description "Optional owner name of the SAA operation";
                }

                leaf test {
                    type types-sros:named-item;
                    description "SAA test name";
                }

                leaf admin-state {
                    type types-sros:admin-state;
                    default "disable";
                    description "Administrative state of the SAA test";
                }

                leaf description {
                    type types-sros:description;
                    description "Text description";
                }

                leaf accounting-policy {
                    type leafref {
                        path "../../../log/accounting-policy/policy-id";
                    }
                    sros-ext:auto-restart-to-modify;
                    description "Accounting policy associated with the SAA test";
                }

                leaf continuous {
                    type boolean;
                    sros-ext:auto-restart-to-modify;
                    default "false";
                    description "Execute the SAA tests as continuous";
                }

                leaf probe-history {
                    type enumeration {
                        enum keep                           { value 1; }
                        enum drop                           { value 2; }
                        enum auto                           { value 3; }
                    }
                    sros-ext:auto-restart-to-modify;
                    default "auto";
                    description "History probe behavior";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list jitter-event {
                    key "direction threshold-type";
                    description "Enter the jitter-event list instance";

                    leaf direction {
                        type types-oam:saa-threshold-direction;
                        description "Direction for OAM ping responses for OAM ping test run";
                    }

                    leaf threshold-type {
                        type enumeration {
                            enum rising                         { value 1; }
                            enum falling                        { value 2; }
                        }
                        description "Threshold type";
                    }

                    leaf threshold {
                        type uint32 {
                            range "0..2147483647";
                        }
                        units "microseconds";
                        mandatory true;
                        description "Threshold jitter value";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list jitter-event

                list latency-event {
                    key "direction threshold-type";
                    description "Enter the latency-event list instance";

                    leaf direction {
                        type types-oam:saa-threshold-direction;
                        description "Direction for OAM ping responses for OAM ping test run";
                    }

                    leaf threshold-type {
                        type enumeration {
                            enum rising                         { value 1; }
                            enum falling                        { value 2; }
                        }
                        description "Threshold type";
                    }

                    leaf threshold {
                        type uint32 {
                            range "0..2147483647";
                        }
                        units "microseconds";
                        mandatory true;
                        description "Threshold latency value";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list latency-event

                list loss-event {
                    key "direction threshold-type";
                    description "Enter the loss-event list instance";

                    leaf direction {
                        type types-oam:saa-threshold-direction;
                        description "Direction for OAM ping responses for OAM ping test run";
                    }

                    leaf threshold-type {
                        type enumeration {
                            enum rising                         { value 1; }
                            enum falling                        { value 2; }
                        }
                        description "Threshold type";
                    }

                    leaf threshold {
                        type uint32 {
                            range "0..2147483647";
                        }
                        units "packets";
                        mandatory true;
                        description "Threshold loss event value";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list loss-event

                container type {
                    description "Enter the type context";

                    choice saa-types {
                        case saa-dns {

                            container dns {
                                presence "Enable the dns context";
                                description "Enable the dns context";

                                leaf target-address {
                                    type types-sros:string-not-all-spaces {
                                        length "1..255";
                                    }
                                    mandatory true;
                                    description "DNS name to be resolved to an IP address";
                                }

                                leaf name-server {
                                    type types-sros:ip-address;
                                    mandatory true;
                                    description "IP address of the DNS name server used for the test";
                                }

                                leaf count {
                                    type uint32 {
                                        range "1..100";
                                    }
                                    units "packets";
                                    default "1";
                                    description "Number of messages to send in a sample window";
                                }

                                leaf interval {
                                    type uint32 {
                                        range "1..10";
                                    }
                                    units "seconds";
                                    default "1";
                                    description "Minimum time before the next message request is sent";
                                }

                                leaf source-address {
                                    type types-sros:ip-address;
                                    description "IP address on the local system";
                                }

                                leaf timeout {
                                    type uint32 {
                                        range "1..120";
                                    }
                                    units "seconds";
                                    default "5";
                                    description "Maximum time to wait for a reply message";
                                }

                                leaf router-instance {
                                    type string;
                                    default "_Base_and_management";
                                    description "Router name or VPRN service name";
                                }

                                leaf record-type {
                                    type enumeration {
                                        enum ipv4-a-record                  { value 1; }
                                        enum ipv6-aaaa-record               { value 2; }
                                    }
                                    default "ipv4-a-record";
                                    description "Record type";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                container trap-generation {
                                    description "Enter the trap-generation context";

                                    leaf probe-fail {
                                        type boolean;
                                        default "false";
                                        description "Enable the generation of probe fail notifications";
                                    }

                                    leaf test-complete {
                                        type boolean;
                                        default "false";
                                        description "Enable generation of test complete notifications";
                                    }

                                    leaf test-fail {
                                        type boolean;
                                        default "false";
                                        description "Enable the generation of test fail notifications";
                                    }

                                    leaf probe-fail-threshold {
                                        type uint32 {
                                            range "0..15";
                                        }
                                        default "1";
                                        description "Consecutive probe failure count";
                                    }

                                    leaf test-fail-threshold {
                                        type uint32 {
                                            range "0..15";
                                        }
                                        default "1";
                                        description "Total probe failures for trap generation";
                                    }

                                } // container trap-generation

                            } // container dns

                        }
                        case saa-eth-cfm-loopback {

                            container eth-cfm-loopback {
                                presence "Enable the eth-cfm-loopback context";
                                description "Enable the eth-cfm-loopback context";

                                leaf destination {
                                    type union {
                                        type types-sros:mac-unicast-address-no-zero;
                                        type uint32 {
                                            range "1..8191";
                                        }
                                    }
                                    mandatory true;
                                    description "Destination MAC address or remote MEP ID of the peer";
                                }

                                leaf mep {
                                    type types-eth-cfm:mep-id-type;
                                    mandatory true;
                                    description "Source Ethernet MEP ID";
                                }

                                leaf md-admin-name {
                                    type union {
                                        type types-sros:named-item-64;
                                        type types-eth-cfm:admin-name;
                                    }
                                    mandatory true;
                                    description "Source Ethernet Maintenance Domain (MD) name";
                                }

                                leaf ma-admin-name {
                                    type union {
                                        type types-sros:named-item-64;
                                        type types-eth-cfm:admin-name;
                                    }
                                    mandatory true;
                                    description "Source Ethernet Maintenance Association (MA) name";
                                }

                                leaf count {
                                    type uint32 {
                                        range "1..100";
                                    }
                                    units "packets";
                                    default "1";
                                    description "Number of packets to send";
                                }

                                leaf interval {
                                    type uint32 {
                                        range "1..10";
                                    }
                                    units "seconds";
                                    default "5";
                                    description "Interval between packets sent";
                                }

                                leaf size {
                                    type uint32 {
                                        range "0..1500";
                                    }
                                    units "bytes";
                                    default "0";
                                    description "Size of the value field in the sent frames";
                                }

                                leaf timeout {
                                    type uint32 {
                                        range "1..10";
                                    }
                                    units "seconds";
                                    default "5";
                                    description "Maximum time to wait for a reply packet";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                container qos {
                                    description "Enter the qos context";

                                    leaf fc {
                                        type types-sros:fc-name;
                                        default "nc";
                                        description "FC for the sent echo request packets";
                                    }

                                    leaf profile {
                                        type types-qos:profile-in-out;
                                        default "in";
                                        description "QoS profile for the sent echo request packets";
                                    }

                                } // container qos

                                container trap-generation {
                                    description "Enter the trap-generation context";

                                    leaf probe-fail {
                                        type boolean;
                                        default "false";
                                        description "Enable the generation of probe fail notifications";
                                    }

                                    leaf test-complete {
                                        type boolean;
                                        default "false";
                                        description "Enable generation of test complete notifications";
                                    }

                                    leaf test-fail {
                                        type boolean;
                                        default "false";
                                        description "Enable the generation of test fail notifications";
                                    }

                                    leaf probe-fail-threshold {
                                        type uint32 {
                                            range "0..15";
                                        }
                                        default "1";
                                        description "Consecutive probe failure count";
                                    }

                                    leaf test-fail-threshold {
                                        type uint32 {
                                            range "0..15";
                                        }
                                        default "1";
                                        description "Total probe failures for trap generation";
                                    }

                                } // container trap-generation

                            } // container eth-cfm-loopback

                        }
                        case saa-icmp-ping {

                            container icmp-ping {
                                presence "Enable the icmp-ping context";
                                description "Enable the icmp-ping context";

                                leaf destination-address {
                                    type union {
                                        type types-sros:ip-address;
                                        type types-sros:string-not-all-spaces {
                                            length "1..128";
                                        }
                                    }
                                    mandatory true;
                                    description "Destination IP address or DNS name to send ping request";
                                }

                                leaf count {
                                    type uint32 {
                                        range "1..100000";
                                    }
                                    units "packets";
                                    default "5";
                                    description "ICMP Echo Request packets to send in a sample window";
                                }

                                leaf do-not-fragment {
                                    type boolean;
                                    default "false";
                                    description "Do not fragment echo request packets (valid for IPv4)";
                                }

                                leaf interval {
                                    type union {
                                        type uint32 {
                                            range "1..10000";
                                        }
                                        type decimal64 {
                                            range "0.01..100.00";
                                            fraction-digits 2;
                                        }
                                    }
                                    units "seconds";
                                    default "1";
                                    description "Minimum time to expire before message request is sent";
                                }

                                leaf pattern {
                                    type types-oam:padding-pattern;
                                    default "sequential";
                                    description "Pattern to fill the data portion in a ping packet";
                                }

                                leaf router-instance {
                                    type string;
                                    default "Base";
                                    description "Router name or VPRN service name";
                                }

                                leaf size {
                                    type uint32 {
                                        range "0..16384";
                                    }
                                    units "bytes";
                                    default "56";
                                    description "Packet padding size";
                                }

                                leaf source-address {
                                    type types-sros:ip-address;
                                    description "Source IP address";
                                }

                                leaf timeout {
                                    type uint32 {
                                        range "1..10";
                                    }
                                    units "seconds";
                                    default "5";
                                    description "Time router waits for a reply after sending last probe";
                                }

                                leaf ttl {
                                    type uint32 {
                                        range "1..128";
                                    }
                                    default "64";
                                    description "Time to live in the IP header";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                choice saa-icmp-ping-routing {
                                    default "case-bypass-routing";
                                    case case-bypass-routing {

                                        leaf bypass-routing {
                                            type boolean;
                                            default "false";
                                            description "Bypass routing table for directly connected interfaces";
                                        }

                                    }
                                    case case-interface {

                                        leaf interface {
                                            type types-sros:interface-name;
                                            description "Interface name";
                                        }

                                    }
                                    case case-next-hop-address {

                                        leaf next-hop-address {
                                            type types-sros:ip-address;
                                            description "Next-hop IP address to reach destination";
                                        }

                                    }
                                }
                                container qos {
                                    description "Enter the qos context";

                                    leaf fc {
                                        type types-sros:fc-name;
                                        default "nc";
                                        description "Forwarding class";
                                    }

                                    leaf tos {
                                        type uint32 {
                                            range "0..255";
                                        }
                                        default "0";
                                        description "Type of service";
                                    }

                                } // container qos

                                container trap-generation {
                                    description "Enter the trap-generation context";

                                    leaf probe-fail {
                                        type boolean;
                                        default "false";
                                        description "Enable the generation of probe fail notifications";
                                    }

                                    leaf test-complete {
                                        type boolean;
                                        default "false";
                                        description "Enable generation of test complete notifications";
                                    }

                                    leaf test-fail {
                                        type boolean;
                                        default "false";
                                        description "Enable the generation of test fail notifications";
                                    }

                                    leaf probe-fail-threshold {
                                        type uint32 {
                                            range "0..15";
                                        }
                                        default "1";
                                        description "Consecutive probe failure count";
                                    }

                                    leaf test-fail-threshold {
                                        type uint32 {
                                            range "0..15";
                                        }
                                        default "1";
                                        description "Total probe failures for trap generation";
                                    }

                                } // container trap-generation

                            } // container icmp-ping

                        }
                        case saa-lsp-ping {

                            container lsp-ping {
                                presence "Enable the lsp-ping context";
                                description "Enable the lsp-ping context";

                                leaf interval {
                                    type uint32 {
                                        range "1..10";
                                    }
                                    units "seconds";
                                    default "1";
                                    description "Minimum time before the next lsp-ping request is sent";
                                }

                                leaf send-count {
                                    type uint32 {
                                        range "1..100";
                                    }
                                    units "packets";
                                    default "1";
                                    description "Number of request packets to send in a sample window";
                                }

                                leaf size {
                                    type uint32 {
                                        range "1..9786";
                                    }
                                    units "bytes";
                                    default "1";
                                    description "Packet pad size";
                                }

                                leaf source-ip-address {
                                    type types-sros:ip-address;
                                    description "Source IP address";
                                }

                                leaf timeout {
                                    type uint32 {
                                        range "1..10";
                                    }
                                    units "seconds";
                                    default "5";
                                    description "Time router waits for a reply to an echo request";
                                }

                                leaf ttl {
                                    type uint32 {
                                        range "1..255";
                                    }
                                    default "255";
                                    description "TTL value for the echo request MPLS label";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                container qos {
                                    description "Enter the qos context";

                                    leaf fc {
                                        type types-sros:fc-name;
                                        default "be";
                                        description "Forwarding class";
                                    }

                                    leaf profile {
                                        type types-qos:profile-in-out;
                                        default "out";
                                        description "Profile";
                                    }

                                } // container qos

                                container sub-type {
                                    description "Enter the sub-type context";

                                    choice saa-lsp-ping-sub-type {
                                        case case-sub-type-bgp-label {

                                            container bgp-label {
                                                presence "Enable the bgp-label context";
                                                description "Enable the bgp-label context";

                                                leaf prefix {
                                                    type types-sros:ip-prefix;
                                                    mandatory true;
                                                    description "Destination IP prefix for the test";
                                                }

                                                container path-destination {
                                                    description "Enter the path-destination context";

                                                    leaf ip-address {
                                                        type types-sros:ip-address;
                                                        description "IP address of the path destination";
                                                    }

                                                    choice path-destination-egress {
                                                        case case-interface {

                                                            leaf interface {
                                                                type types-sros:interface-name;
                                                                description "Egress router interface used with the path destination";
                                                            }

                                                        }
                                                        case case-next-hop {

                                                            leaf next-hop {
                                                                type types-sros:ip-address;
                                                                description "Egress IP next hop address used with path destination";
                                                            }

                                                        }
                                                    }
                                                } // container path-destination

                                            } // container bgp-label

                                        }
                                        case case-sub-type-ldp {

                                            container ldp {
                                                presence "Enable the ldp context";
                                                description "Enable the ldp context";

                                                leaf prefix {
                                                    type types-sros:ip-prefix;
                                                    mandatory true;
                                                    description "Destination IP prefix for the test";
                                                }

                                                container path-destination {
                                                    description "Enter the path-destination context";

                                                    leaf ip-address {
                                                        type types-sros:ip-address;
                                                        description "IP address of the path destination";
                                                    }

                                                    choice path-destination-egress {
                                                        case case-interface {

                                                            leaf interface {
                                                                type types-sros:interface-name;
                                                                description "Egress router interface used with the path destination";
                                                            }

                                                        }
                                                        case case-next-hop {

                                                            leaf next-hop {
                                                                type types-sros:ip-address;
                                                                description "Egress IP next hop address used with path destination";
                                                            }

                                                        }
                                                    }
                                                } // container path-destination

                                            } // container ldp

                                        }
                                        case case-sub-type-rsvp-te {

                                            container rsvp-te {
                                                presence "Enable the rsvp-te context";
                                                description "Enable the rsvp-te context";

                                                leaf lsp-name {
                                                    type types-sros:named-item-64;
                                                    mandatory true;
                                                    description "Name of the LSP to be tested";
                                                }

                                                leaf path {
                                                    type types-sros:named-item-64;
                                                    description "Name of the MPLS path to be tested";
                                                }

                                            } // container rsvp-te

                                        }
                                        case case-sub-type-sr-isis {

                                            container sr-isis {
                                                presence "Enable the sr-isis context";
                                                description "Enable the sr-isis context";

                                                leaf prefix {
                                                    type types-sros:ip-prefix;
                                                    mandatory true;
                                                    description "Destination IP prefix for the test";
                                                }

                                                leaf igp-instance {
                                                    type uint32 {
                                                        range "0..127";
                                                    }
                                                    default "0";
                                                    description "IGP instance for the SR IS-IS test";
                                                }

                                                container path-destination {
                                                    description "Enter the path-destination context";

                                                    leaf ip-address {
                                                        type types-sros:ip-address;
                                                        description "IP address of the path destination";
                                                    }

                                                    choice path-destination-egress {
                                                        case case-interface {

                                                            leaf interface {
                                                                type types-sros:interface-name;
                                                                description "Egress router interface used with the path destination";
                                                            }

                                                        }
                                                        case case-next-hop {

                                                            leaf next-hop {
                                                                type types-sros:ip-address;
                                                                description "Egress IP next hop address used with path destination";
                                                            }

                                                        }
                                                    }
                                                } // container path-destination

                                            } // container sr-isis

                                        }
                                        case case-sub-type-sr-ospf {

                                            container sr-ospf {
                                                presence "Enable the sr-ospf context";
                                                description "Enable the sr-ospf context";

                                                leaf prefix {
                                                    type types-sros:ip-prefix;
                                                    mandatory true;
                                                    description "Destination IP prefix for the test";
                                                }

                                                leaf igp-instance {
                                                    type uint32 {
                                                        range "0..31";
                                                    }
                                                    default "0";
                                                    description "IGP instance for the SR OSPF test";
                                                }

                                                container path-destination {
                                                    description "Enter the path-destination context";

                                                    leaf ip-address {
                                                        type types-sros:ip-address;
                                                        description "IP address of the path destination";
                                                    }

                                                    choice path-destination-egress {
                                                        case case-interface {

                                                            leaf interface {
                                                                type types-sros:interface-name;
                                                                description "Egress router interface used with the path destination";
                                                            }

                                                        }
                                                        case case-next-hop {

                                                            leaf next-hop {
                                                                type types-sros:ip-address;
                                                                description "Egress IP next hop address used with path destination";
                                                            }

                                                        }
                                                    }
                                                } // container path-destination

                                            } // container sr-ospf

                                        }
                                        case case-sub-type-sr-ospf3 {

                                            container sr-ospf3 {
                                                presence "Enable the sr-ospf3 context";
                                                description "Enable the sr-ospf3 context";

                                                leaf prefix {
                                                    type types-sros:ip-prefix;
                                                    mandatory true;
                                                    description "Destination IP prefix for the test";
                                                }

                                                leaf igp-instance {
                                                    type uint32 {
                                                        range "0..31|64..95";
                                                    }
                                                    default "0";
                                                    description "IGP instance for the SR OSPFv3 test";
                                                }

                                                container path-destination {
                                                    description "Enter the path-destination context";

                                                    leaf ip-address {
                                                        type types-sros:ip-address;
                                                        description "IP address of the path destination";
                                                    }

                                                    choice path-destination-egress {
                                                        case case-interface {

                                                            leaf interface {
                                                                type types-sros:interface-name;
                                                                description "Egress router interface used with the path destination";
                                                            }

                                                        }
                                                        case case-next-hop {

                                                            leaf next-hop {
                                                                type types-sros:ip-address;
                                                                description "Egress IP next hop address used with path destination";
                                                            }

                                                        }
                                                    }
                                                } // container path-destination

                                            } // container sr-ospf3

                                        }
                                        case case-sub-type-sr-policy {

                                            container sr-policy {
                                                presence "Enable the sr-policy context";
                                                description "Enable the sr-policy context";

                                                leaf color {
                                                    type int64 {
                                                        range "0..4294967295";
                                                    }
                                                    mandatory true;
                                                    description "Segment Routing color for the test";
                                                }

                                                leaf endpoint {
                                                    type types-sros:ip-address;
                                                    mandatory true;
                                                    description "Segment Routing endpoint for the test";
                                                }

                                                leaf segment-list {
                                                    type uint32 {
                                                        range "1..32";
                                                    }
                                                    description "Segment Routing segment list for the test";
                                                }

                                                container path-destination {
                                                    description "Enter the path-destination context";

                                                    leaf ip-address {
                                                        type types-sros:ip-address;
                                                        description "IP address of the path destination";
                                                    }

                                                    choice path-destination-egress {
                                                        case case-interface {

                                                            leaf interface {
                                                                type types-sros:interface-name;
                                                                description "Egress router interface used with the path destination";
                                                            }

                                                        }
                                                        case case-next-hop {

                                                            leaf next-hop {
                                                                type types-sros:ip-address;
                                                                description "Egress IP next hop address used with path destination";
                                                            }

                                                        }
                                                    }
                                                } // container path-destination

                                            } // container sr-policy

                                        }
                                        case case-sub-type-sr-te {

                                            container sr-te {
                                                presence "Enable the sr-te context";
                                                description "Enable the sr-te context";

                                                leaf lsp-name {
                                                    type types-sros:named-item-64;
                                                    mandatory true;
                                                    description "Name of the LSP to be tested";
                                                }

                                                leaf path {
                                                    type types-sros:named-item-64;
                                                    description "Name of the MPLS path to be tested";
                                                }

                                                container path-destination {
                                                    description "Enter the path-destination context";

                                                    leaf ip-address {
                                                        type types-sros:ip-address;
                                                        description "IP address of the path destination";
                                                    }

                                                    choice path-destination-egress {
                                                        case case-interface {

                                                            leaf interface {
                                                                type types-sros:interface-name;
                                                                description "Egress router interface used with the path destination";
                                                            }

                                                        }
                                                        case case-next-hop {

                                                            leaf next-hop {
                                                                type types-sros:ip-address;
                                                                description "Egress IP next hop address used with path destination";
                                                            }

                                                        }
                                                    }
                                                } // container path-destination

                                            } // container sr-te

                                        }
                                    }
                                } // container sub-type

                                container trap-generation {
                                    description "Enter the trap-generation context";

                                    leaf probe-fail {
                                        type boolean;
                                        default "false";
                                        description "Enable the generation of probe fail notifications";
                                    }

                                    leaf test-complete {
                                        type boolean;
                                        default "false";
                                        description "Enable generation of test complete notifications";
                                    }

                                    leaf test-fail {
                                        type boolean;
                                        default "false";
                                        description "Enable the generation of test fail notifications";
                                    }

                                    leaf probe-fail-threshold {
                                        type uint32 {
                                            range "0..15";
                                        }
                                        default "1";
                                        description "Consecutive probe failure count";
                                    }

                                    leaf test-fail-threshold {
                                        type uint32 {
                                            range "0..15";
                                        }
                                        default "1";
                                        description "Total probe failures for trap generation";
                                    }

                                } // container trap-generation

                            } // container lsp-ping

                        }
                        case saa-sdp-ping {

                            container sdp-ping {
                                presence "Enable the sdp-ping context";
                                description "Enable the sdp-ping context";

                                leaf originating-sdp-identifier {
                                    type uint32 {
                                        range "1..32767";
                                    }
                                    mandatory true;
                                    description "SDP ID used to send packets";
                                }

                                leaf responder-sdp-identifier {
                                    type uint32 {
                                        range "1..32767";
                                    }
                                    description "SDP ID used by the far-end to reply to the request";
                                }

                                leaf count {
                                    type uint32 {
                                        range "1..100";
                                    }
                                    units "packets";
                                    default "1";
                                    description "Number of SDP echo request packets to send";
                                }

                                leaf interval {
                                    type uint32 {
                                        range "1..10";
                                    }
                                    units "seconds";
                                    default "1";
                                    description "Interval between SDP echo request packets sent";
                                }

                                leaf size {
                                    type uint32 {
                                        range "72..9786";
                                    }
                                    units "bytes";
                                    default "72";
                                    description "Size of the SDP echo request packets";
                                }

                                leaf timeout {
                                    type uint32 {
                                        range "1..10";
                                    }
                                    units "seconds";
                                    default "5";
                                    description "Maximum time to wait for SDP echo reply packets";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                container qos {
                                    description "Enter the qos context";

                                    leaf fc {
                                        type types-sros:fc-name;
                                        default "be";
                                        description "FC for the transmitted SDP echo request packets";
                                    }

                                    leaf profile {
                                        type types-qos:profile-in-out;
                                        default "out";
                                        description "QoS profile for transmitted SDP echo request packets";
                                    }

                                } // container qos

                                container trap-generation {
                                    description "Enter the trap-generation context";

                                    leaf probe-fail {
                                        type boolean;
                                        default "false";
                                        description "Enable the generation of probe fail notifications";
                                    }

                                    leaf test-complete {
                                        type boolean;
                                        default "false";
                                        description "Enable generation of test complete notifications";
                                    }

                                    leaf test-fail {
                                        type boolean;
                                        default "false";
                                        description "Enable the generation of test fail notifications";
                                    }

                                    leaf probe-fail-threshold {
                                        type uint32 {
                                            range "0..15";
                                        }
                                        default "1";
                                        description "Consecutive probe failure count";
                                    }

                                    leaf test-fail-threshold {
                                        type uint32 {
                                            range "0..15";
                                        }
                                        default "1";
                                        description "Total probe failures for trap generation";
                                    }

                                } // container trap-generation

                            } // container sdp-ping

                        }
                        case saa-vccv-ping {

                            container vccv-ping {
                                presence "Enable the vccv-ping context";
                                description "Enable the vccv-ping context";

                                leaf count {
                                    type uint32 {
                                        range "1..100";
                                    }
                                    units "packets";
                                    default "1";
                                    description "Number of echo request packets to send";
                                }

                                leaf interval {
                                    type uint32 {
                                        range "1..10";
                                    }
                                    units "seconds";
                                    default "1";
                                    description "Interval between packets sent";
                                }

                                leaf size {
                                    type uint32 {
                                        range "1..9786";
                                    }
                                    units "bytes";
                                    default "1";
                                    description "Echo request packet pad size";
                                }

                                leaf timeout {
                                    type uint32 {
                                        range "1..10";
                                    }
                                    units "seconds";
                                    default "5";
                                    description "Wait time for a reply after sending an echo request";
                                }

                                leaf ttl {
                                    type uint32 {
                                        range "1..255";
                                    }
                                    default "1";
                                    description "TTL value for the echo request MPLS label";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                container qos {
                                    description "Enter the qos context";

                                    leaf fc {
                                        type types-sros:fc-name;
                                        default "be";
                                        description "QoS FC for the sent echo request packets";
                                    }

                                    leaf profile {
                                        type types-qos:profile-in-out;
                                        default "out";
                                        description "QoS profile for the sent echo request packets";
                                    }

                                } // container qos

                                container sub-type {
                                    description "Enter the sub-type context";

                                    choice saa-vccv-ping-sub-type {
                                        case case-sub-type-fec-128 {

                                            container fec-128 {
                                                presence "Enable the fec-128 context";
                                                description "Enable the fec-128 context";

                                                leaf sdp-bind-id {
                                                    type types-services:sdp-bind-id;
                                                    mandatory true;
                                                    description "SDP bind ID to test";
                                                }

                                                leaf reply-mode {
                                                    type enumeration {
                                                        enum ip-routed                      { value 2; }
                                                        enum control-channel                { value 4; }
                                                    }
                                                    default "control-channel";
                                                    description "In-band or out-of-band reply";
                                                }

                                                container pseudowire {
                                                    presence "Enable the pseudowire context";
                                                    description "Enable the pseudowire context";

                                                    leaf destination-ip-address {
                                                        type types-sros:ipv4-address;
                                                        mandatory true;
                                                        description "PW destination IP address";
                                                    }

                                                    leaf source-ip-address {
                                                        type types-sros:ipv4-address;
                                                        mandatory true;
                                                        description "PW source IP address";
                                                    }

                                                    leaf pw-id {
                                                        type uint32 {
                                                            range "1..4294967295";
                                                        }
                                                        mandatory true;
                                                        description "PW identifier";
                                                    }

                                                } // container pseudowire

                                            } // container fec-128

                                        }
                                    }
                                } // container sub-type

                                container trap-generation {
                                    description "Enter the trap-generation context";

                                    leaf probe-fail {
                                        type boolean;
                                        default "false";
                                        description "Enable the generation of probe fail notifications";
                                    }

                                    leaf test-complete {
                                        type boolean;
                                        default "false";
                                        description "Enable generation of test complete notifications";
                                    }

                                    leaf test-fail {
                                        type boolean;
                                        default "false";
                                        description "Enable the generation of test fail notifications";
                                    }

                                    leaf probe-fail-threshold {
                                        type uint32 {
                                            range "0..15";
                                        }
                                        default "1";
                                        description "Consecutive probe failure count";
                                    }

                                    leaf test-fail-threshold {
                                        type uint32 {
                                            range "0..15";
                                        }
                                        default "1";
                                        description "Total probe failures for trap generation";
                                    }

                                } // container trap-generation

                            } // container vccv-ping

                        }
                    }
                } // container type

            } // list owner

        } // container saa

    } // grouping conf-saa

}
